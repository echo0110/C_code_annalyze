LTE-ENB-MIB DEFINITIONS ::= BEGIN


-- *************************************************************************
-- * File Name    : LTE-ENB-MIB.mib
-- * Description  : This file contains the SNMP MIB objects for LTE eNodeB
-- *
-- * Revision History
-- * ================
-- * Date        Author             Version         Comments
-- * ==========  =============      =======    =============================
-- * 09/07/2013  Supriya Sharma      v0.1      Initial Draft
-- * 25/07/2013  Vivek Kumar Gupta   v0.2      Change in the structure of MIB
-- * 26/07/2013  Vivek Kumar Gupta   v0.3      First scaled-down draft for a
-- *                                           stable MIB
-- * 31/07/2013  Vivek Kumar Gupta   v0.4      More Nodes added 
-- * 31/07/2013  Sonu Yadav          v0.5      MIB validation.
-- * 31/07/2013  Vivek Kumar Gupta   v0.6.1    MIB validation. 
-- * 31/07/2013  Nitin Vijay         v0.6.2    More Nodes added.
-- * 31/07/2013  Vivek Kumar Gupta   v0.6.3    Merging & minor updates
-- * 31/07/2013  Vivek Kumar Gupta   v0.6.4    MIB validation success by
-- *                                           snmptranslate and code
-- *                                           generation successful from
-- *                                           mib2c tool
-- * 01/08/2013  Sonu Yadav          v0.7.0    MIB validation.
-- * 01/08/2013  Vivek Kumar Gupta   v0.8.0    Updated the top level hierarchy
-- *                                           of the mib.
-- * 01/08/2013  Vivek Kumar Gupta   v1.0.0    First draft version finalized
-- *                                           and validated by smilint
-- * 05/08/2013  Vivek Kumar Gupta   v1.0.1    Corrected data types of some
-- *                                           wrongly typed objects according
-- *                                           to TR-196i2.0.0
-- * 05/08/2013  Vivek Kumar Gupta   v1.0.2    Added all the FaultMgmt objects
-- * 07/08/2013  Vivek Kumar Gupta   v1.0.3    Added description clause for
-- *                                           all the nodes
-- * 07/08/2013  Vivek Kumar Gupta   v1.0.4    Incorporated some review comments
-- * 12/08/2013  Vivek Kumar Gupta   v1.0.5    Incorporated some review comments
-- * 12/08/2013  Vivek Kumar Gupta   v1.0.6    Incorporated some review comments
-- *                                           and added trap information
-- * 13/08/2013  Vivek Kumar Gupta   v1.0.7    Changes in the MIB tree and some
-- *                                           nodes added/deleted
-- * 21/08/2013  Vivek Kumar Gupta   v1.0.8    Minor updates
-- * 24/09/2013  Vivek Kumar Gupta   v1.0.9    Change in the SYNTAX field
-- *                                           of fileWriteTimer object
-- * 25/09/2013  Vivek Kumar Gupta   v1.0.10   Change in the DESCRIPTION
-- *                                           field of plmnListTblIsPrimary
-- *                                           object.
-- * 28/09/2013  Manoj Kumar         v1.0.11   Added example values for the PerfMgmt parameters.
-- * 07/10/2013  Vivek K Gupta       v1.0.12   Added a note in the description
-- *                                           of allowedCipheringAlgorithmList
-- *                                           & allowedIntegrityProtectionAlgorithmList;
-- *                                           Added two new notification-types
-- * 19/11/2013  Ashish Sharma       v1.0.13   Range of freqBandIndicator changed from 40 to 43 for CSR-00056169
-- * 25/04/2014  Ekta Jain           v1.0.14   Addition of Parameters for multi cell support
-- * 28 May 2014 Avnish				SPR 10257 Code changes
-- * 16/06/2014  Ekta Jain           v1.0.15   Addition of Alarms(Alarm Id 161-165)
--                                             Deletion of Alarm Id 157,160
-- * copyright {Copyright (c) 2013, Aricent Inc. All Rights Reserved}
-- **************************************************************************

IMPORTS
        OBJECT-TYPE, Integer32, MODULE-IDENTITY,
        Unsigned32, enterprises,
        NOTIFICATION-TYPE                            FROM SNMPv2-SMI

        TEXTUAL-CONVENTION, DisplayString            FROM SNMPv2-TC;

enb MODULE-IDENTITY
    LAST-UPDATED "201507310000Z"
    ORGANIZATION "*************"
    CONTACT-INFO "*************"
    DESCRIPTION
        "This MIB represents the eNodeB management parameters described in
         TR-196 2.0.0, TR-157-v1.5.0, and TR-262 v1.0"
    REVISION     "201507310000Z"
    DESCRIPTION
        "Added EMBMS related objects and traps"
    REVISION     "201407240000Z"
    DESCRIPTION
        "Added notification types: x2apAssociationLinkDownAlarm,
         x2apAssociationLinkUpAlarm
         and splitted the existing notification type: 
         oamSonPCIConflictConfusionNotification into two different
         notification types: pciConfusionNotification, pciConflictNotification"
    REVISION     "201406160000Z"
    DESCRIPTION
        "Added Alarm Ids (161-165)
         macPhyOAMErrorMsgInvalidState,macPhyOAMErrorSFNOutofsyncByMoreThanThreshold,
         macPhyOAMErrMsgBCHmissing,macPhyOAMerrMsgHiErr,oamSonPCIConflictConfusionNotification"
    REVISION     "201405050000Z"
    DESCRIPTION
        "Added Parameters(enbConfiguredCID,enbCurrentCID) for multi cell support"
    REVISION     "201311190000Z"
    DESCRIPTION
        "Range of freqBandIndicator changed from 40 to 43 for CSR-00056169"
    REVISION     "201310070000Z"
    DESCRIPTION
        "Added a note in the description of allowedCipheringAlgorithmList
         & allowedIntegrityProtectionAlgorithmList;
         Added two new notification-types: hmResponseNotRecvdAlarm, and
         childKillSignalAlarm"
    REVISION     "201309280000Z"
    DESCRIPTION
        "Added example values for the PerfMgmt parameters"
    REVISION     "201309250000Z"
    DESCRIPTION
        "Change in the DESCRIPTION field of plmnListTblIsPrimary object"
    REVISION     "201309240000Z"
    DESCRIPTION
        "Change in the SYNTAX field of the object fileWriteTimer"
    REVISION     "201308210000Z"
    DESCRIPTION
        "Minor updates"
    REVISION     "201308130000Z"
    DESCRIPTION
        "Changes in the MIB tree and some nodes added/deleted."
    REVISION     "201308121625Z"
    DESCRIPTION
        "Incorporated some review comments and added trap information."
    REVISION     "201308120000Z"
    DESCRIPTION
        "Incorporated some review comments and removed inconsistencies with
         OAM."
    REVISION     "201308070000Z"
    DESCRIPTION
        "Added missing description clause in some objects. Incorporated some
         review."
    REVISION     "201308050000Z"
    DESCRIPTION
        "Corrected data types of some wrongly typed objects according to
         TR-196 2.0.0. Added FaultMgmt objects."
    REVISION     "201308010000Z"
    DESCRIPTION
        "MIB validation. Updated the top level hierarchy of the mib. First
         draft version finalized and validated by smilint."
    REVISION     "201307310000Z"
    DESCRIPTION
        "More Nodes added. MIB validation. Merging & minor updates. MIB
         validation success by snmptranslate and code generation successful
         from mib2c tool"
    REVISION     "201307260000Z"
    DESCRIPTION
        "First scaled-down draft for a stable MIB."
    REVISION     "201307250000Z"
    DESCRIPTION
        "Change in the structure of MIB."
    REVISION     "201307090000Z"
    DESCRIPTION
        "Initial Draft."
::= { enterprises aricent-communication-holding-ltd(29601) lte(11) 20 }


-- FIRST LEVEL PARENT NODES
-- ------------------------

internetGatewayDevice         OBJECT IDENTIFIER ::= { enb 1 }
lteeNodeBTraps                OBJECT IDENTIFIER ::= { enb 2 }

deviceInfo                    OBJECT IDENTIFIER ::= { internetGatewayDevice 1 }

-- This object contains parameters relating to Performance Management 
perfMgmt                      OBJECT IDENTIFIER ::= { internetGatewayDevice 2 }
 
services                      OBJECT IDENTIFIER ::= { internetGatewayDevice 3 }
faultMgmt                     OBJECT IDENTIFIER ::= { internetGatewayDevice 4 }

-- SECOND LEVEL PARENT NODES
-- -------------------------

enbService                    OBJECT IDENTIFIER ::= { services 2 }

trapObjects                    OBJECT IDENTIFIER ::= { lteeNodeBTraps 1 }

-- THIRD LEVEL PARENT NODES
-- ------------------------

--This object contains parameters relating to File Management configuration
-- for uploading of Performance Files to a designated File Server.
perfMgmtConfig                OBJECT IDENTIFIER ::= { perfMgmt 2 }


-- The below object contains parameters relating to the hardware capabilities
-- of the device.
capabilities                  OBJECT IDENTIFIER ::= { enbService 3 }


enbControl                    OBJECT IDENTIFIER ::= { enbService 4 }


-- Below object contains parameters relating to Access Management for the
-- different radio technologies.
accessMgmt                    OBJECT IDENTIFIER ::= { enbService 5 }

-- This object contains parameters relating to configuring the device.
cellConfig                    OBJECT IDENTIFIER ::= { enbService 6 }
transport                     OBJECT IDENTIFIER ::= { enbService 7 }
enbTrapParams                 OBJECT IDENTIFIER ::= { trapObjects 1 }
enbTrapObjects                OBJECT IDENTIFIER ::= { trapObjects 2 }
enbVendorSpecificTrapObjects  OBJECT IDENTIFIER ::= { trapObjects 3 }



-- FOURTH LEVEL PARENT NODES
-- -------------------------

-- Below object contains parameters relating to the system and RF aspect of
-- the device that supports the UMTS system.
capabilitiesLTE               OBJECT IDENTIFIER ::= { capabilities 5 }

-- Below object contains parameters relating to the LTE system specific
-- information.
enbState                      OBJECT IDENTIFIER ::= { enbControl 1 }

-- Below object contains parameters relating to Access Management, as defined
-- in [3GPP-TS.32.592]
-- Closed Subscriber Group (CSG) service behavior is specified in
-- [3GPP-TS.22.011].
-- Note: Cell barring and 3GPP access class parameters are contained in SIB1
-- in [3GPP-TS.36.331].
accessMgmtLTE                 OBJECT IDENTIFIER ::= { accessMgmt 1 }


cellConfigLTE                 OBJECT IDENTIFIER ::= { cellConfig 1 }

-- The parameters under sctp are modifiable only if the adminState is
-- unlocked.
sctp                          OBJECT IDENTIFIER ::= { transport 1 }

software                      OBJECT IDENTIFIER ::= { enbTrapObjects 1 }
link                          OBJECT IDENTIFIER ::= { enbTrapObjects 2 }
rrhTraps                      OBJECT IDENTIFIER ::= { enbVendorSpecificTrapObjects 1 }
cpriTraps                     OBJECT IDENTIFIER ::= { enbVendorSpecificTrapObjects 2 }
rcmTraps                      OBJECT IDENTIFIER ::= { enbVendorSpecificTrapObjects 3 }
miscTraps                     OBJECT IDENTIFIER ::= { enbVendorSpecificTrapObjects 4 }

--SPR 14225 start
cellConfigEICIC                         OBJECT IDENTIFIER ::= { cellConfig 2 }
--SPR 14225 end

-- FIFTH LEVEL PARENT NODES
-- -------------------------

-- Below object contains parameters relating to the Gateways that the LTE device
-- is connected to.
gateway                       OBJECT IDENTIFIER ::= { enbState 4 }

epc                           OBJECT IDENTIFIER ::= { cellConfigLTE 1 }
ran                           OBJECT IDENTIFIER ::= { cellConfigLTE 2 }

--SPR 14225 start
eICICProvisionType            OBJECT IDENTIFIER ::= { cellConfigEICIC 1 }
absInfo                       OBJECT IDENTIFIER ::= { cellConfigEICIC 2 }
eligibleUe                    OBJECT IDENTIFIER ::= { cellConfigEICIC 3 }
eicicTimerInfo                OBJECT IDENTIFIER ::= { cellConfigEICIC 4 }
dlSinrThreshLowMark           OBJECT IDENTIFIER ::= { cellConfigEICIC 5 }
dlSinrThreshHighMark          OBJECT IDENTIFIER ::= { cellConfigEICIC 6 }
--SPR 14225 end

-- SIXTH LEVEL PARENT NODES
-- -------------------------

common                        OBJECT IDENTIFIER ::= { ran 1 }
s1AP                          OBJECT IDENTIFIER ::= { ran 2 }
rf                            OBJECT IDENTIFIER ::= { ran 3 }
phy                           OBJECT IDENTIFIER ::= { ran 4 }
mac                           OBJECT IDENTIFIER ::= { ran 5 }
rlc                           OBJECT IDENTIFIER ::= { ran 6 }
rrcTimers                     OBJECT IDENTIFIER ::= { ran 7 }
cellRestriction               OBJECT IDENTIFIER ::= { ran 8 }
mobility                      OBJECT IDENTIFIER ::= { ran 9 }
neighborList                  OBJECT IDENTIFIER ::= { ran 10 }
neighborListInUse             OBJECT IDENTIFIER ::= { ran 11 }

--SPR 14225 start
numAbsReport                    OBJECT IDENTIFIER ::= { absInfo 1 }
absUsageLowThreshold            OBJECT IDENTIFIER ::= { absInfo 2 } 
absUsageHighThreshold           OBJECT IDENTIFIER ::= { absInfo 3 }
absPattern                      OBJECT IDENTIFIER ::= { absInfo 4 }
macEicicMeasReportPeriodicity   OBJECT IDENTIFIER ::= { eicicTimerInfo 1 }
aggressorSelTimer               OBJECT IDENTIFIER ::= { eicicTimerInfo 2 }
loadInformationGuardTimer       OBJECT IDENTIFIER ::= { eicicTimerInfo 3 }
loadInformationCollationTimer   OBJECT IDENTIFIER ::= { eicicTimerInfo 4 }

--SPR 14225 end

-- SEVENTH LEVEL PARENT NODES
-- -------------------------

idleMode                      OBJECT IDENTIFIER ::= { mobility 1 }
connMode                      OBJECT IDENTIFIER ::= { mobility 2 }
antennaInfo                   OBJECT IDENTIFIER ::= { phy 1 }
pdsch                         OBJECT IDENTIFIER ::= { phy 2 }
srs                           OBJECT IDENTIFIER ::= { phy 3 }
prach                         OBJECT IDENTIFIER ::= { phy 4 }
pucch                         OBJECT IDENTIFIER ::= { phy 5 }
pusch                         OBJECT IDENTIFIER ::= { phy 6 }
ulPowerControl                OBJECT IDENTIFIER ::= { phy 7 }
mbsfn                         OBJECT IDENTIFIER ::= { phy 8 }
prs                           OBJECT IDENTIFIER ::= { phy 9 }
tddFrame                      OBJECT IDENTIFIER ::= { phy 10 }
rach                          OBJECT IDENTIFIER ::= { mac 1 }
drx                           OBJECT IDENTIFIER ::= { mac 2 }
srb1                          OBJECT IDENTIFIER ::= { rlc 1 }
srb2                          OBJECT IDENTIFIER ::= { rlc 2 }
neighborListInterRATCell      OBJECT IDENTIFIER ::= { neighborList 4 }
neighborListInUseInterRATCell OBJECT IDENTIFIER ::= { neighborListInUse 4 }

--SPR 14225 start
lowLoadAbsPattern             OBJECT IDENTIFIER ::= { absPattern 1 } 
victimAbsPattern              OBJECT IDENTIFIER ::= { absPattern 2 }
victimMeasSubset              OBJECT IDENTIFIER ::= { absPattern 3 }
--SPR 14225 end

-- EIGTH LEVEL PARENT NODES
-- -------------------------

idleModeCommon                OBJECT IDENTIFIER ::= { idleMode 1 }
intraFreq                     OBJECT IDENTIFIER ::= { idleMode 2 }
interFreq                     OBJECT IDENTIFIER ::= { idleMode 3 }
idleModeIRAT                  OBJECT IDENTIFIER ::= { idleMode 4 }
eutra                         OBJECT IDENTIFIER ::= { connMode 1 }
connModeIRAT                  OBJECT IDENTIFIER ::= { connMode 2 }
ulrs                          OBJECT IDENTIFIER ::= { pusch 5 }

-- NINETH LEVEL PARENT NODES
-- -------------------------

utra                          OBJECT IDENTIFIER ::= { idleModeIRAT 1 }
geran                         OBJECT IDENTIFIER ::= { idleModeIRAT 2 }



BoolType ::= TEXTUAL-CONVENTION
STATUS      current
DESCRIPTION "Boolean data type"
SYNTAX      INTEGER { false(0), true(1) }



TReselectionSFType ::= TEXTUAL-CONVENTION
STATUS      current
DESCRIPTION "Enumeration values for TReselectionSF parameters"
SYNTAX      INTEGER { oDot25(25), oDot5(50), oDot75(75), lDot0(100) }


--SPR 14225 start
ProvisionTypeeICIC   ::= TEXTUAL-CONVENTION
STATUS      current
DESCRIPTION "Enumeration values for eICIC Provision Type"
SYNTAX      INTEGER{ fc0(0), fc1(1), fc2(2), fc3(3)}
--SPR 14225 end

FilteringCoefficientType ::= TEXTUAL-CONVENTION
STATUS                         current
DESCRIPTION                    "Enumeration of filtering coefficient values"
SYNTAX                         INTEGER { fc0(0), fc1(1), fc2(2), fc3(3),
                                         fc4(4), fc5(5), fc6(6), fc7(7),
                                         fc8(8), fc9(9), fc11(11), fc13(13),
                                         fc15(15), fc17(17), fc19(19)
                                       }



TimeToTriggerType ::= TEXTUAL-CONVENTION
STATUS                  current
DESCRIPTION             "Enumeration of time-to-trigger values"
SYNTAX                  INTEGER { ms0(0), ms40(40), ms64(64), ms80(80),
                                  ms100(100), ms128(128), ms160(160),
                                  ms256(256), ms320(320), ms480(480),
                                  ms512(512), ms640(640), ms1024(1024),
                                  ms1280(1280), ms2560(2560), ms5120(5120)
                                }



ReportIntervalType ::= TEXTUAL-CONVENTION
STATUS                   current
DESCRIPTION              "Enumeration of report interval values"
SYNTAX                   INTEGER { ms120(120), ms240(240), ms480(480),
                                   ms640(640), ms1024(1024), ms2048(2048),
                                   ms5120(5120), ms10240(10240), min1(60000),
                                   min6(360000), min12(720000),
                                   min30(1800000), min60(3600000)
                                 }



ReportAmountType ::= TEXTUAL-CONVENTION
STATUS                 current
DESCRIPTION            "Enumeration of report amount values"
SYNTAX                   INTEGER { infinity(0), r1(1), r2(2), r4(4), r8(8),
                                   r16(16), r32(32), r64(64)
                                 }




QOffsetType ::= TEXTUAL-CONVENTION
STATUS              current
DESCRIPTION         "Enumeration values for QOffset"
SYNTAX              INTEGER { dBMinus24(-24), dBMinus22(-22),
                              dBMinus20(-20), dBMinus18(-18),
                              dBMinus16(-16), dBMinus14(-14),
                              dBMinus12(-12), dBMinus10(-10),
                              dBMinus8(-8),   dBMinus6(-6),
                              dBMinus5(-5),   dBMinus4(-4),
                              dBMinus2(-2),   dBMinus1(-1),
                              dB0(0), dB1(1), dB2(2), dB3(3),
                              dB4(4), dB5(5), dB6(6), dB8(8),
                              dB10(10), dB12(12), dB14(14), dB16(16),
                              dB18(18), dB20(20), dB22(22), dB24(24)
                            }




TPollRetransmitType ::= TEXTUAL-CONVENTION
STATUS              current
DESCRIPTION         "Eumeration for TPollRetransmit values"
SYNTAX              INTEGER { ms5(5), ms10(10), ms15(15), ms20(20), ms25(25),
                              ms30(30), ms35(35), ms40(40), ms45(45),
                              ms50(50), ms55(55), ms60(60), ms65(65),
                              ms70(70), ms75(75), ms80(80), ms85(85),
                              ms90(90), ms95(95), ms100(100), ms105(105),
                              ms110(110), ms115(115), ms120(120), ms125(125),
                              ms130(130), ms135(135), ms140(140), ms145(145),
                              ms150(150), ms155(155), ms160(160), ms165(165),
                              ms170(170), ms175(175), ms180(180), ms185(185),
                              ms190(190), ms195(195), ms200(200), ms205(205),
                              ms210(210), ms215(215), ms220(220), ms225(225),
                              ms230(230), ms235(235), ms240(240), ms245(245),
                              ms250(250), ms300(300), ms350(350), ms400(400),
                              ms450(450), ms500(500)
                            }




PollPDUType ::= TEXTUAL-CONVENTION
STATUS        current
DESCRIPTION   "Eumeration values for PollPDU parameter"
SYNTAX        INTEGER { pInfinity(0), p4(4), p8(8), p16(16), p32(32),
                        p64(64), p128(128), p256(256)
                      }




PollByteType ::= TEXTUAL-CONVENTION
STATUS        current
DESCRIPTION   "Eumeration values for PollByte parameter"
SYNTAX        INTEGER { kBinfinity(0), kB25(25), kB50(50), kB75(75),
                        kB100(100), kB125(125), kB250(250), kB375(375),
                        kB500(500), kB750(750), kB1000(1000), kB1250(1250),
                        kB1500(1500), kB2000(2000), kB3000(3000)
                      }




MaxRetxThresholdType ::= TEXTUAL-CONVENTION
STATUS        current
DESCRIPTION   "Eumeration values for MaxRetxThreshold parameter"
SYNTAX        INTEGER { t1(1), t2(2), t3(3), t4(4),
                        t6(6), t8(8), t16(16), t32(32)
                      }




TReorderingType ::= TEXTUAL-CONVENTION
STATUS        current
DESCRIPTION   "Eumeration values for TReordering parameter"
SYNTAX        INTEGER { ms0(0), ms5(5), ms10(10), ms15(15), ms20(20),
                            ms25(25), ms30(30), ms35(35), ms40(40), ms45(45),
                            ms50(50), ms55(55), ms60(60), ms65(65), ms70(70),
                            ms75(75), ms80(80), ms85(85), ms90(90), ms95(95),
                            ms100(100), ms110(110), ms120(120), ms130(130),
                            ms140(140), ms150(150), ms160(160), ms170(170),
                            ms180(180), ms190(190), ms200(200)
                          }




TStatusProhibitType ::= TEXTUAL-CONVENTION
STATUS        current
DESCRIPTION   "Eumeration values for TStatusProhibit parameter"
SYNTAX        INTEGER { ms0(0), ms5(5), ms10(10), ms15(15), ms20(20),
                        ms25(25), ms30(30), ms35(35), ms40(40),
                        ms45(45), ms50(50), ms55(55), ms60(60),
                        ms65(65), ms70(70), ms75(75), ms80(80),
                        ms85(85), ms90(90), ms95(95), ms100(100),
                        ms105(105), ms110(110), ms115(115), ms120(120),
                        ms125(125), ms130(130), ms135(135), ms140(140),
                        ms145(145), ms150(150), ms155(155), ms160(160),
                        ms165(165), ms170(170), ms175(175), ms180(180),
                        ms185(185), ms190(190), ms195(195), ms200(200),
                        ms205(205), ms210(210), ms215(215), ms220(220),
                        ms225(225), ms230(230), ms235(235), ms240(240),
                        ms245(245), ms250(250), ms300(300), ms350(350),
                        ms400(400), ms450(450), ms500(500)
                      }




TimerType1 ::= TEXTUAL-CONVENTION
STATUS        current
DESCRIPTION   "Eumeration values for t300, t301, t302 parameter"
SYNTAX        INTEGER { ms100(100), ms200(200), ms300(300), ms400(400),
                      ms600(600), ms1000(1000), ms1500(1500), ms2000(2000)
                    }




T304EUTRAType ::= TEXTUAL-CONVENTION
STATUS        current
DESCRIPTION   "Eumeration values for t304EUTRA parameter"
SYNTAX        INTEGER { ms50(50), ms100(100), ms150(150), ms200(200),
                        ms600(600), ms1000(1000), ms2000(2000)
                      }




T304IRATType ::= TEXTUAL-CONVENTION
STATUS        current
DESCRIPTION   "Eumeration values for t304IRAT parameter"
SYNTAX        INTEGER { ms100(100), ms200(200), ms500(500), ms1000(1000),
                        ms2000(2000), ms4000(4000), ms8000(8000)
                      }




T310Type ::= TEXTUAL-CONVENTION
STATUS        current
DESCRIPTION   "Eumeration values for t310 parameter"
SYNTAX        INTEGER { ms0(0), ms50(50), ms100(100), ms200(200), ms500(500),
                        ms1000(1000), ms2000(2000)
                    }




T311Type ::= TEXTUAL-CONVENTION
STATUS        current
DESCRIPTION   "Eumeration values for t311 parameter"
SYNTAX        INTEGER  { ms1000(1000), ms3000(3000), ms5000(5000),
                         ms10000(10000), ms15000(15000), ms20000(20000),
                         ms30000(30000)
                       }




T320Type ::= TEXTUAL-CONVENTION
STATUS        current
DESCRIPTION   "Eumeration values for t320 parameter"
SYNTAX        INTEGER { min5(5), min10(10), m20(20), min30(30),
                        min60(60), min120(120), min180(180)
                      }




N310Type ::= TEXTUAL-CONVENTION
STATUS        current
DESCRIPTION   "Eumeration values for n310 parameter"
SYNTAX        INTEGER { n1(1), n2(2), n3(3), n4(4), n6(6), n8(8),
                        n10(10), n20(20)
                      }




N311Type ::= TEXTUAL-CONVENTION
STATUS        current
DESCRIPTION   "Eumeration values for n311 parameter"
SYNTAX        INTEGER { n1(1), n2(2), n3(3), n4(4), n5(5),
                        n6(6), n8(8), n10(10)
                      }



QHystType ::= TEXTUAL-CONVENTION
STATUS        current
DESCRIPTION   "Eumeration values for QHyst parameter"
SYNTAX        INTEGER { dB0(0), dB1(1), dB2(2), dB3(3), dB4(4), dB5(5),
                        dB6(6), dB8(8), dB10(10), dB12(12), dB14(14),
                        dB16(16), dB18(18), dB20(20), dB22(22), dB24(24)
                      }



QHystSFType ::= TEXTUAL-CONVENTION
STATUS          current
DESCRIPTION     "Enumeration of QHystSF values"
SYNTAX          INTEGER { dBMinus6(-6),
                          dBMinus4(-4),
                          dBMinus2(-2),
                          dB0(0)
                        }



TEvaluationType ::= TEXTUAL-CONVENTION
STATUS          current
DESCRIPTION     "Enumeration of TEvaluation values"
SYNTAX          INTEGER { s30(30), s60(60), s120(120), s180(180), s240(240) }




PaType ::= TEXTUAL-CONVENTION
STATUS              current
DESCRIPTION         "Enumeration values for Pa parameter"
SYNTAX              INTEGER { dBMinus6(-600), dBMinus4dot77(-477),
                              dBMinus3(-300), dBMinus1dot77(-177), dB0(0),
                              dB1(100), dB2(200), dB3(300)
                            }




AlphaType ::= TEXTUAL-CONVENTION
STATUS              current
DESCRIPTION         "Enumeration values for alpha parameter"
SYNTAX              INTEGER { al0(0), al04(40), al05(50), al06(60),
                              al07(70), al08(80), al09(90), al1(100)
                            }




DeltaFPUCCHFormat1Type ::= TEXTUAL-CONVENTION
STATUS              current
DESCRIPTION         "Enumeration values for DeltaFPUCCHFormat1 parameter"
SYNTAX              INTEGER { deltaFMinus2(-2), deltaF0(0), deltaF2(2) }




DeltaFPUCCHFormat1bType ::= TEXTUAL-CONVENTION
STATUS              current
DESCRIPTION         "Enumeration values for DeltaFPUCCHFormat1b parameter"
SYNTAX              INTEGER { deltaF1(1), deltaF3(3), deltaF5(5) }




DeltaFPUCCHFormat2Type ::= TEXTUAL-CONVENTION
STATUS              current
DESCRIPTION         "Enumeration values for DeltaFPUCCHFormat2 parameter"
SYNTAX              INTEGER { deltaFMinus2(-2), deltaF0(0), deltaF2(2) }




DeltaFPUCCHFormat2aType ::= TEXTUAL-CONVENTION
STATUS              current
DESCRIPTION         "Enumeration values for DeltaFPUCCHFormat2a parameter"
SYNTAX              INTEGER { deltaFMinus2(-2), deltaF0(0), deltaF2(2) }




DeltaFPUCCHFormat2bType ::= TEXTUAL-CONVENTION
STATUS              current
DESCRIPTION         "Enumeration values for DeltaFPUCCHFormat2b parameter"
SYNTAX              INTEGER { deltaFMinus2(-2), deltaF0(0), deltaF2(2) }


ENBCtrlActionType ::= TEXTUAL-CONVENTION
STATUS              current
DESCRIPTION         "Enumeration values for cell operations"
SYNTAX              INTEGER { noaction(0), celldelete(1), cellsetup(2),
                              cellstop(3), cellstart(4), cellblock(5),
                              cellunblock(6)
                            }

ENBSWUpdateActionType ::= TEXTUAL-CONVENTION
STATUS              current
DESCRIPTION         "Enumeration values for software update actions"
SYNTAX              INTEGER { noaction(0), download(1), switch(2) }



AntennaPortsCountType ::= TEXTUAL-CONVENTION
STATUS              current
DESCRIPTION         "Enumeration values for antennaPortsCount"
SYNTAX              INTEGER { an1(1), an2(2), an4(4) }




enbServiceNumberOfEntries     OBJECT-TYPE
SYNTAX                        Unsigned32 
MAX-ACCESS                    read-only
STATUS                        current
DESCRIPTION
" Defaults to 1, indicates support for single enbService table entry."
::= { services 1 }


manufacturer        OBJECT-TYPE
SYNTAX              DisplayString (SIZE(1..64))
MAX-ACCESS          read-only
STATUS              current
DESCRIPTION
"
The manufacturer of the CPE (human readable string).
"
::= { deviceInfo 1 }   


manufacturerOUI     OBJECT-TYPE
SYNTAX              DisplayString (SIZE(1..6))
MAX-ACCESS          read-only
STATUS              current
DESCRIPTION
"
Organizationally unique identifier of the device manufacturer. Represented as
a six hexadecimal-digit value using all upper-case letters and including any
leading zeros. The value MUST be a valid OUI as defined in [OUI].

This value MUST remain fixed over the lifetime of the device, including
across firmware updates.
"
::= { deviceInfo 2 }     


modelName           OBJECT-TYPE
SYNTAX              DisplayString (SIZE(1..64))
MAX-ACCESS          read-only
STATUS              current
DESCRIPTION
"
Model name of the CPE (human readable string).
"
::= { deviceInfo 3 }


description         OBJECT-TYPE
SYNTAX              DisplayString (SIZE(1..256))
MAX-ACCESS          read-only
STATUS              current
DESCRIPTION
"
A full description of the CPE device (human readable string).
"
::= { deviceInfo 4 }


productClass        OBJECT-TYPE
SYNTAX              DisplayString (SIZE(1..64))
MAX-ACCESS          read-only
STATUS              current
DESCRIPTION
"
Identifier of the class of product for which the serial number applies. That
is, for a given manufacturer, this parameter is used to identify the product
or class of product over which the SerialNumber parameter is unique.

This value MUST remain fixed over the lifetime of the device, including
across firmware updates.
"
::= { deviceInfo 5 }


serialNumber        OBJECT-TYPE
SYNTAX              DisplayString (SIZE(1..64))
MAX-ACCESS          read-only
STATUS              current
DESCRIPTION
"
Serial number of the CPE.
This value MUST remain fixed over the lifetime of the device, including
across firmware updates.
"
::= { deviceInfo 6 }


hardwareVersion     OBJECT-TYPE
SYNTAX              DisplayString (SIZE(1..64))
MAX-ACCESS          read-only
STATUS              current
DESCRIPTION
"
A string identifying the particular CPE model and version.
"
::= { deviceInfo 7 }


softwareVersion     OBJECT-TYPE
SYNTAX              DisplayString (SIZE(1..64))
MAX-ACCESS          read-only
STATUS              current
DESCRIPTION
"
A string identifying the software version currently installed in the CPE.

To allow version comparisons, this element SHOULD be in the form of
dot-delimited integers, where each successive integer represents a more minor
category of variation. For example, 3.0.21 where the components mean:
Major.Minor.Build.
"
::= { deviceInfo 8 }

modemFirmwareVersion    OBJECT-TYPE
SYNTAX                  DisplayString (SIZE(1..64))
MAX-ACCESS              read-only
STATUS                  current
DESCRIPTION
"
A string identifying the version of the modem firmware currently installed in
the CPE. This is applicable only when the modem firmware is separable from
the overall CPE software.
"
::= { deviceInfo 9 }


additionalSoftwareVersion   OBJECT-TYPE
SYNTAX                      DisplayString (SIZE(1..64))
MAX-ACCESS                  read-only
STATUS                      current
DESCRIPTION
"
Comma-separated list (maximum length 64) of strings. Any additional software
version information the vendor might wish to supply.
"
::= { deviceInfo 10 }


upTime          OBJECT-TYPE
SYNTAX          Unsigned32 
MAX-ACCESS      read-only
STATUS          current
DESCRIPTION
"
Time in seconds since the CPE was last restarted.
"
::= { deviceInfo 11 }


firstUseDate    OBJECT-TYPE
SYNTAX          DisplayString
MAX-ACCESS      read-only
STATUS          current
DESCRIPTION
"
Date and time in UTC that the CPE first both successfully established an
IP-layer network connection and acquired an absolute time reference using NTP
or equivalent over that network connection. The CPE MAY reset this date after
a factory reset.

If NTP or equivalent is not available, this parameter, if present, SHOULD be
set to the Unknown Time value.
"
::= { deviceInfo 12 }



configNumberOfEntries   OBJECT-TYPE
SYNTAX                  Unsigned32
MAX-ACCESS              read-only
STATUS                  current
DESCRIPTION
"
The number of entries in the perfMgmtConfig table.
"
::= { perfMgmt 1 }

url             OBJECT-TYPE
SYNTAX          DisplayString (SIZE(1..256))
MAX-ACCESS      read-write
STATUS          current
DESCRIPTION
"
URL specifying the destination file location. 
The FTP address must be configured in the FTP path (ftp://<ftp-server-address>) format 
e.g. ftp://192.168.0.2. 
This argument specifies only the destination file location, and does not
indicate in any way the name or location of the local file to be uploaded.
"
::= { perfMgmtConfig 1 }


userName        OBJECT-TYPE
SYNTAX          DisplayString (SIZE(1..256))
MAX-ACCESS      read-write
STATUS          current
DESCRIPTION
"
Username to be used by the device to authenticate with the file server. This
string is set to an empty string if no authentication is used.
"
::= { perfMgmtConfig 2}


password        OBJECT-TYPE
SYNTAX          DisplayString (SIZE(1..256))
MAX-ACCESS      read-write
STATUS          current
DESCRIPTION
"
Password to be used by the device to authenticate with the file server. This
string is set to an empty string if no authentication is used.

When read, this parameter returns an empty string, regardless of the actual
value.
"
::= { perfMgmtConfig 3 }


periodicUploadInterval     OBJECT-TYPE
SYNTAX                     Unsigned32
MAX-ACCESS                 read-write
STATUS                     current
DESCRIPTION
"
The duration in seconds of the interval for which the device MUST create a
Performance File and attempt to upload the file to URL if Enable is true. 
Two possible values 3600 or 86400 seconds are supported for this parameter. 
e.g. if the value is set to 3600 seconds (1 hour), the file upload is done after every hour.
"
::= { perfMgmtConfig 4 }


periodicUploadTime OBJECT-TYPE
SYNTAX             DisplayString
MAX-ACCESS         read-write
STATUS             current
DESCRIPTION
"
An absolute time reference in UTC to determine when the device will initiate
the periodic file upload. Each file upload MUST occur at this reference time
plus or minus an integer multiple of the PeriodicUploadInterval. 
Example value format: 2013-02-01T09:09:00Z

PeriodicUploadTime is used only to set the 'phase' of the periodic uploads.
The actual value of PeriodicUploadTime can be arbitrarily far into the past
or future.

For example, if PeriodicUploadInterval is 86400 (a day) and if
PeriodicUploadTime is set to UTC midnight on some day (in the past, present,
or future) then periodic file uploads will occur every day at UTC midnight.
These MUST begin on the very next midnight, even if PeriodicUploadTime refers
to a day in the future.

The Unknown Time value as defined in [Section 3.2/TR-106a4] indicates that no
particular time reference is specified. That is, the device MAY locally
choose the time reference, and is REQUIRED only to adhere to the specified
PeriodicUploadInterval.

If absolute time is not available to the device, its periodic file upload
behavior MUST be the same as if the PeriodicUploadTime parameter was set to
the Unknown Time value.
"
::= { perfMgmtConfig 5 }


fileWriteTimer OBJECT-TYPE
SYNTAX  Unsigned32 (5..60)
MAX-ACCESS read-write
STATUS current
DESCRIPTION
"
PURPOSE: This is the interval in minutes at which LTE OAM shall perform write operation in PM XML file when periodic reporting is enabled.
e.g. if this interval is set to 10 minutes, the PM XML file is updated every 10 minutes.
"
DEFVAL { 10 }
::= { perfMgmtConfig 6 }


samplingIntervalTimer     OBJECT-TYPE
SYNTAX                    Unsigned32 (5..60)
MAX-ACCESS                read-write
STATUS                    current
DESCRIPTION
"
PURPOSE: This is the interval in minutes at which KPIs information is collected from eNB layers when periodic reporting of KPIs is enabled.
For example, if sampling interval timer is set as 10 minutes, the KPIs are collected at every 10 minutes.
"
DEFVAL { 10 }
::= { perfMgmtConfig 7 }


deviceType        OBJECT-TYPE
SYNTAX            DisplayString (SIZE(1..10))
MAX-ACCESS        read-only
STATUS            current
DESCRIPTION
"
The type of device. Enumeration of:
  * Standalone
  * Integrated 

"
::= { enbService 1 }


dnPrefix        OBJECT-TYPE
SYNTAX          DisplayString (SIZE(1..256))
MAX-ACCESS      read-only
STATUS          current
DESCRIPTION
"
The Distinguished Name prefix (DNPrefix) is an operator-configurable prefix
string that is pre-pended to object distinguished names in the [TR-157a5]
alarm object. See [3GPP-TS.32.300] for the formal definition and examples of
DNPrefix as applied to 3GPP alarm objects
"
::= { enbService 2 }


gpsEquipped        OBJECT-TYPE
SYNTAX             BoolType
MAX-ACCESS         read-only
STATUS             current
DESCRIPTION
"
Indicates whether the device is equipped with a GPS receiver or not.
"
::= { capabilities 1 }


maxTxPower           OBJECT-TYPE
SYNTAX               Unsigned32
MAX-ACCESS           read-only
STATUS               current
DESCRIPTION
"
Indicates the maximum possible transmit power in dBm that the device hardware 
can support.
"
::= { capabilities 2 }


supportedSystems       OBJECT-TYPE
SYNTAX                 DisplayString
MAX-ACCESS             read-only
STATUS                 current
DESCRIPTION
"
Comma-separated list of strings. Each entry is a type of system that the device
supports. Each list item is an enumeration of:
  * UMTS
  * LTE
  * CDMA1x
  * CDMAHRPD 
"
::= { capabilities 3 }


beacon            OBJECT-TYPE
SYNTAX            BoolType
MAX-ACCESS        read-only
STATUS            current
DESCRIPTION
"
Indicates whether device can support beacon transmission.
"
::= { capabilities 4 }


duplexMode       OBJECT-TYPE
SYNTAX           DisplayString
MAX-ACCESS       read-only
STATUS           current
DESCRIPTION
"
Indicates the mode supported by the LTE device. Enumeration of:
  * FDDMode 
  * TDDMode
"
::= { capabilitiesLTE 1 }


bandsSupported OBJECT-TYPE
SYNTAX         DisplayString (SIZE(1..16))
MAX-ACCESS     read-only
STATUS         current
DESCRIPTION
"
Comma-separated list (maximum length 16) (at least 1 items) of unsigned
integers (value 1 to 21, or 33 to 40). Indicates the LTE bands that the LTE
device supports [Section 5.5/3GPP-TS.36.101]. At least one band MUST be
supported and multiple bands MAY be supported.

Each individual band is identified by arabic number (1, 2,...). The order of
the band indicators in the string has no significance.

In case a new band is defined in the 3GPP standard in a future release of
[3GPP-TS.36.101], the corresponding new band number will be included in the
valid band indicators.

The followings are examples of valid values:

    '1' (specifies only band-1 is supported) 
    '1,2,11' (specifies 3 bands are supported) 
    '2,11,1' (specifies 3 bands are supported) 
"
::= { capabilitiesLTE 2 }


nnsfSupported       OBJECT-TYPE
SYNTAX              BoolType
MAX-ACCESS          read-only
STATUS              current
DESCRIPTION
"
Indicates whether LTE device supports the NAS Node Selection Function (NNSF) or
not. NNSF is described in [Section 19.2.1.7 and Section 4.6.1/3GPP-TS.36.300].
"
::= { capabilitiesLTE 3 }


umtsRxSupported     OBJECT-TYPE
SYNTAX              BoolType
MAX-ACCESS          read-only
STATUS              current
DESCRIPTION
"
Indicates whether the LTE device hardware supports the receiving function of
UMTS or not.
"
::= { capabilitiesLTE 4 }


umtsRxBandsSupported        OBJECT-TYPE
SYNTAX                      DisplayString (SIZE(1..16))
MAX-ACCESS                  read-only
STATUS                      current
DESCRIPTION
"
Comma-separated list (maximum length 16) of strings. Indicates the UMTS
receive bands that the LTE device supports [3GPP-TS.25.104], Release 8. If
UMTSRxSupported is true, then at least one band MUST be supported and
multiple bands MAY be supported.

Each individual band is identified by its upper case Roman numeral. The order
of the band indicators in the string has no significance.

In case a new band is defined in the 3GPP standard in a future release of
[3GPP-TS.25.104], the corresponding new upper case Roman numeral will be
included in the valid band indicators.

The followings are examples of valid values:
    `I` (specifies only band-I is supported) 
    `I,II,V` (specifies 3 bands are supported) 
    `II,VII,I` (specifies 3 bands are supported) 
"
::= { capabilitiesLTE 5 }


gsmRxSupported       OBJECT-TYPE
SYNTAX               BoolType
MAX-ACCESS           read-only
STATUS               current
DESCRIPTION
"
Indicates whether the LTE device hardware supports the receiving function of
GSM or not.
"
::= { capabilitiesLTE 6 }


gsmRxBandsSupported     OBJECT-TYPE
SYNTAX                  DisplayString
MAX-ACCESS              read-only
STATUS                  current
DESCRIPTION
"
Comma-separated list of strings. Indicates the GSM receive bands that the
LTE device supports [3GPP-TS.45.005]. If GSMRxSupported is true, then at least
one band MUST be supported and multiple bands MAY be supported.

[3GPP-TS.45.005] defines 14 GSM bands. Each list item is an enumeration of:

  * T-GSM380
  * T-GSM410
  * GSM450
  * GSM480
  * GSM710
  * GSM750
  * T-GSM810
  * GSM850
  * P-GSM900
  * E-GSM900
  * R-GSM900
  * T-GSM900
  * DCS1800
  * PCS1900 

The order of the band indicators in the string has no significance.

The following is an example of a valid value.

    'GSM850,PCS1900' 
"
::= { capabilitiesLTE 7 }


cdma2000RxSupported         OBJECT-TYPE
SYNTAX                      BoolType
MAX-ACCESS                  read-only
STATUS                      current
DESCRIPTION
"
Indicates whether the LTE device hardware supports the receiving function of
CDMA2000 or not.
"
::= { capabilitiesLTE 8 }


cdma2000RxBandsSupported    OBJECT-TYPE
SYNTAX                      DisplayString (SIZE(1..16))
MAX-ACCESS                  read-only
STATUS                      current
DESCRIPTION
"
Comma-separated list (maximum length 16) of strings. Indicates the CDMA2000
receive bands that the LTE device supports. If CDMA2000RxSupported is true, then
at least one band MUST be supported and multiple bands MAY be supported. The
order of the band indicators in the string has no significance. Bandclass is
a 1 or 2-digit number as defined in [3GPP2-C.S0057-B].

The following are example values:

    '0' (specifies US Cellular) 
    '1,3,14' (specifies US PCS, Japan Cellular and US PCS 1.9Ghz) specifies 3
bands are supported) 
"
::= { capabilitiesLTE 9 }


opState         OBJECT-TYPE
SYNTAX          BoolType
MAX-ACCESS      read-only
STATUS          current
DESCRIPTION
"
Current operational state of the LTE device as defined in [ITU-X.731].

If true the LTE device is currently enabled.

If false the LTE device is currently disabled
"
::= { enbState 1 }


adminState     OBJECT-TYPE
SYNTAX         BoolType
MAX-ACCESS     read-write
STATUS         current
DESCRIPTION
"
Lock or unlock the LTE device. This controls the administrative state of the LTE
device as defined in [ITU-X.731].

If true Unlocked with permission to serve traffic (and enable RF
transmitter(s)).

If false Locked. Transition LTE device to state where it is NOT permitted to
serve traffic. RF transmitter is disabled.

Given that this command controls the LTE device's RF transmitter, the underlying
expectation is that the unlock is done when all necessary conditions are met
to allow the transmitter to key on and provide service, including aspects
such as:

  * location verification (including meeting the governing regulatory
    requirements)
  * verifying the LTE device configuration
  * if physical tampering is supported and no physical tampering is detected. 

The default value after power-on is false.
"
DEFVAL { false }
::= { enbState 2 }



rfTxStatus     OBJECT-TYPE
SYNTAX         BoolType
MAX-ACCESS     read-only
STATUS         current
DESCRIPTION
"
Current status of this LTE device RF transmitter.

true indicates that the LTE device Tx transmitter is on.

false indicates that the LTE device Tx transmitter is off.

This state is tied to the Administrative state which is controlled by the
ACS.

When the ACS sets AdminState to true, then the LTE device has permission to
turn on the RF transmitter. 
When the ACS sets AdminState to false, then the LTE device is not allowed to
provide service and MUST turn off the RF transmitter. 
"
::= { enbState 3 }


availabilityStatus     OBJECT-TYPE
SYNTAX Unsigned32 (0..3)
MAX-ACCESS     read-only
STATUS         current
DESCRIPTION
"
Availability Status of the system.
"
DEFVAL { 0 }
::= { enbState 5 }



enbCtrlCellAction    OBJECT-TYPE
SYNTAX               ENBCtrlActionType
MAX-ACCESS           read-write
STATUS               current
DESCRIPTION
"
Control object to control cell operation. Enumeration of:
  * noaction
  * celldelete
  * cellsetup
  * cellstop
  * cellstart
  * cellblock
  * cellunblock
GET for this parameter always returns the value 'noaction'
"
DEFVAL { noaction }
::= { enbControl 2 }



enbSWUpdateAction    OBJECT-TYPE
SYNTAX               ENBSWUpdateActionType
MAX-ACCESS           read-write
STATUS               current
DESCRIPTION
"
Control object to control eNodeB software update. Enumeration of:
  * noaction
  * downlowd
  * switch
"
::= { enbControl 3 }



enbSWImageFile       OBJECT-TYPE
SYNTAX               DisplayString
MAX-ACCESS           read-write
STATUS               current
DESCRIPTION
"
eNodeB software image file path name for enbSWUpdateAction
"
::= { enbControl 4 }
enbConfiguredCID       OBJECT-TYPE
SYNTAX                 DisplayString
MAX-ACCESS           read-only
STATUS               current
DESCRIPTION
"
Comma-separated list of all cells configured
"
::= { enbControl 5 }

enbCurrentCID       OBJECT-TYPE
SYNTAX              Unsigned32(0..7)
MAX-ACCESS           read-write
STATUS               current
DESCRIPTION
"
Current Cell on which action is to be performed
"
::= { enbControl 6 }

-- * SPR FIX 10257 start
secGWServer1 OBJECT-TYPE
SYNTAX DisplayString (SIZE(1..64))
MAX-ACCESS read-write
STATUS current
DESCRIPTION
"
First SecGW the LTE FAP attempts to establish connection with. Either hostname or IPaddress.
"
::= { gateway 1 }


secGWServer2 OBJECT-TYPE
SYNTAX DisplayString (SIZE(1..64))
MAX-ACCESS read-write
STATUS current
DESCRIPTION
"
Second SecGW the LTE FAP attempts to establish connection with. Either hostname or IPaddress.
"
::= { gateway 2 }


secGWServer3 OBJECT-TYPE
SYNTAX DisplayString (SIZE(1..64))
MAX-ACCESS read-write
STATUS current
DESCRIPTION
"
Third SecGW the LTE FAP attempts to establish connection with. Either hostname or IPaddress.
"
::= { gateway 3 }

-- * SPR FIX 10257 end
s1SigLinkServerList OBJECT-TYPE
SYNTAX DisplayString (SIZE(1..256))
MAX-ACCESS read-only
STATUS current
DESCRIPTION
"
Comma-separated list (maximum length 256) (at least 1 items) of strings. Each
item is a S1 signaling connection end point (-GW or MME) the LTE device attempts
to establish connection with. It is in the form of either hostname or
IPaddress. LTE device's behavior in terms of the number of S1 connection to
established with is determined by S1ConnectionMode parameter. If
S1ConnectionMode has the value of One, then LTE device attempts to establish S1
connection with only one address following the ordering of the list. If
S1ConnectionMode has the value of All, then LTE device attempts to establish
connection with all addresses in the list.
"
::= { gateway 4 }


s1SigLinkPort OBJECT-TYPE
SYNTAX Unsigned32 (1..65535)
MAX-ACCESS read-write
STATUS current
DESCRIPTION
"
Port number of S1AP signaling connection end point (-GW or MME) used for
initial S1 SCTP contact. This value is specified as 36412 according to IANA
definition per [IANA-portnumbers], registered on 2009-09-01. Use of
IANA-defined value is recommended.

Note: Write of this parameter not supported after cell configuration. 
"
::= { gateway 5 }


accessMode OBJECT-TYPE
SYNTAX DisplayString
MAX-ACCESS read-write             
STATUS current   
DESCRIPTION
"
Indicates the type of access mode the device operates in. Enumeration of:

  * Open Access (Access control is not enforced. CSG Identity is not
    broadcast)
  * Closed Access (LTE device operates as a CSG cell)
  * Hybrid Access (LTE device operates as a CSG cell where at the same time,
    non-CSG members are allowed access) 

Note: This parameter controls the setting of the CSGindicator bit, specified
in SIB1 in [3GPP-TS.36.331].

The factory default value MUST be Open Access.
"
DEFVAL { "OpenAccess" }
::= { accessMgmtLTE 1 }



maxUEsServed OBJECT-TYPE
SYNTAX Integer32 (-1..255)
MAX-ACCESS read-only
STATUS current
DESCRIPTION
"
Maximum number of concurrent CSG member UEs allowed at a hybrid or closed
cell. A value of -1 allows an unlimited number of CSG members up to the limit
of device capacity. The setting cannot be larger than the value of MaxUEsServed.
The setting does not affect emergency calls. [3GPP-TS.22.011],
[3GPP-TS.22.220].

The factory default value MUST be -1.
"
DEFVAL { -1 }
::= { accessMgmtLTE 2 }


maxCSGMembers OBJECT-TYPE
-- * SPR FIX 10258 start
SYNTAX Integer32 (-1..255)
-- * SPR FIX 10258 end
MAX-ACCESS read-write             
STATUS current   
DESCRIPTION
"
Maximum number of concurrent CSG member UEs allowed at a hybrid or closed
cell. A value of -1 allows an unlimited number of CSG members up to the
limit of device capacity. The setting cannot be larger than the value of
MaxUEsServed. The setting does not affect emergency calls. [3GPP-TS.22.011],
[3GPP-TS.22.220].

The factory default value MUST be -1.

"
DEFVAL { -1 }
::= { accessMgmtLTE 3 }


maxNonCSGMembers OBJECT-TYPE
SYNTAX Integer32 (-1..255)
MAX-ACCESS read-write
STATUS current
DESCRIPTION
"
Maximum number of concurerent non-CSG member UEs allowed at a hybrid cell.
Valid only if AccessMode is Hybrid Access. The setting cannot be larger than
the value of MaxUEsServed. The setting does not affect emergency calls.

The factory default value MUST be -1.
"
DEFVAL { -1 }
::= { accessMgmtLTE 4 }


csgid OBJECT-TYPE
SYNTAX Unsigned32 (0..134217727)
MAX-ACCESS read-write             
STATUS current   
DESCRIPTION
"
Defines the Closed Subscriber Group of the Access Control List. The LTE device
broadcasts this in SIB1, and corresponds to parameter csg-Identity in SIB1 in
[3GPP-TS.36.331].
"
DEFVAL { 8 }
::= { accessMgmtLTE 5 }


hnbName OBJECT-TYPE
SYNTAX DisplayString (SIZE(1..48))
MAX-ACCESS read-write
STATUS current
DESCRIPTION
"
Home NodeB name. An operator-defined string that is broadcast by a CSG cell
or a hybrid cell and displayed on the UE for the purpose of manual cell
selection or indication that the UE is camped on the cell as specified in
[Section 5.4.2/3GPP-TS.22.220]. Corresponds to parameter 'hnb-Name' specified
in SIB9 in [Section 6.3.1/3GPP-TS.36.331].
"
DEFVAL { "lte-eNodeb" }
::= { accessMgmtLTE 6 }


allowedCipheringAlgorithmList OBJECT-TYPE
SYNTAX                        DisplayString
MAX-ACCESS                    read-write
STATUS                        current
DESCRIPTION
"
Comma-separated list (at least 1 items) of strings. Each item is a ciphering
algorithm allowed to be used for RRC and UP confidentiality protection as
defined in [3GPP-TS.33.401]. If the list contains more than 1 item, it is in
the order of the preferred algorithm to be used. Each list item is an
enumeration of:

  * EEA0
  * 128-EEA1
  * 128-EEA2 

NOTE:
    This parameter is configurable only before cell setup.
"
::= { epc 1 }


allowedIntegrityProtectionAlgorithmList OBJECT-TYPE
SYNTAX                                  DisplayString
MAX-ACCESS                              read-write             
STATUS                                  current   
DESCRIPTION
"
Comma-separated list (at least 1 items) of strings. Each item is a integrity
protection algorithm allowed to be used for RRC as defined in
[3GPP-TS.33.401]. If the list contains more than 1 item, it is in the order
of the preferred algorithm to be used. Each list item is an enumeration of:

  * 128-EIA1
  * 128-EIA2 

NOTE:
    This parameter is configurable only before cell setup.
"
::= { epc 2 }


tac                 OBJECT-TYPE
SYNTAX              Unsigned32 (0..65535)
MAX-ACCESS          read-write
STATUS              current
DESCRIPTION
"
TAC (Tracking Area Code) for LTE device as specified in
SystemInformationBlockType1 message in [Section 6.2.2/3GPP-TS.36.331].
"
::= { epc 3 }


eaid                OBJECT-TYPE
SYNTAX              Unsigned32 (0..16777216)
MAX-ACCESS          read-write
STATUS              current
DESCRIPTION
"
Emergency Area ID that uniquely identifies the area of emergency for
Earthquake and Tsunami Warning Services (ETWS). Corresponds to Emergency Area
ID in [Section 9.2.1.47/3GPP-TS.36.413].
"
::= { epc 4 }


maxPLMNListEntries      OBJECT-TYPE
SYNTAX                  Unsigned32
MAX-ACCESS              read-only
STATUS                  current
DESCRIPTION
"
The maximum number of entries available in the
CellConfig.LTE.EPC.PLMNList.{i}. table.
"
::= { epc 5 }


plmnListNumberOfEntries OBJECT-TYPE
SYNTAX                  Unsigned32
MAX-ACCESS              read-only
STATUS                  current
DESCRIPTION
"
The number of entries in the PLMNList table.
"
::= { epc 6 }


qoSNumberOfEntries     OBJECT-TYPE
SYNTAX                 Unsigned32
MAX-ACCESS             read-only
STATUS                 current
DESCRIPTION
"
The number of entries in the QoS table.
"
::= { epc 7 }


plmnListTable   OBJECT-TYPE
SYNTAX SEQUENCE OF PLMNListTableEntry
MAX-ACCESS      not-accessible
STATUS          current
DESCRIPTION
"
This object contains parameters relating to list of PLMN identity specific to
LTE EPC definition, called PLMN-IdentityList, as specified in
SystemInformationBlockType1 message in [Section 6.2.2/3GPP-TS.36.331]. Each
instance in this object is a PLMN-IdentityInfo which consists of
plmn-Identity and cellReservedForOperatorUse IEs. At minimum 1 item MUST be
present in this list, and maximum of 6 items.

This table MUST contain at least 1 and at most 6 entries.

At most one entry in this table (regardless of whether or not it is enabled)
can exist with a given value for Alias. On creation of a new table entry, the
CPE MUST choose an initial value for Alias such that the new entry does not
conflict with any existing entries.

At most one enabled entry in this table can exist with a given value for
PLMNID.
"
::= { epc 8 }


PLMNListTableEntry ::= SEQUENCE {
    plmnListTblIndex                      Unsigned32,
    plmnListTblEnable                     BoolType,
    plmnListTblIsPrimary                  BoolType,
    plmnListTblPLMNID                     DisplayString,
    plmnListTblCellReservedForOperatorUse BoolType
}


plmnListTableEntry         OBJECT-TYPE
SYNTAX                     PLMNListTableEntry
MAX-ACCESS                 not-accessible
STATUS                     current
DESCRIPTION
"
Defines one row in plmnListTable.
"
INDEX { plmnListTblIndex }
::= { plmnListTable 1 }


plmnListTblIndex   OBJECT-TYPE
SYNTAX             Unsigned32
MAX-ACCESS         not-accessible
STATUS             current
DESCRIPTION
"
Index of the plmnListTable row.
"
::= { plmnListTableEntry 1 }


plmnListTblEnable      OBJECT-TYPE
SYNTAX                 BoolType
MAX-ACCESS             read-write
STATUS                 current
DESCRIPTION
"
Enables or disables this entry.
"
::= { plmnListTableEntry 2 }


plmnListTblIsPrimary           OBJECT-TYPE
SYNTAX                         BoolType
MAX-ACCESS                     read-write
STATUS                         current
DESCRIPTION
"
Indicates whether this PLMNID is a primary PLMN or not. If there is more than
one instance in CellConfig.LTE.EPC.PLMNList.{i}. table, then ACS MUST set
this IsPrimary set to true in only one instance.

NOTE:
This parameter can be set to true only for one instance at a time.
"
::= { plmnListTableEntry 3 }


plmnListTblPLMNID    OBJECT-TYPE
SYNTAX               DisplayString
MAX-ACCESS           read-write
STATUS               current
DESCRIPTION
"
PLMN ID consists of Mobile Country Code (MCC) and Mobile Network Code (MNC)
[3GPP-TS.23.003], [3GPP-TS.24.008].

Mobile Country Code consists of three digits and uniquely identifies the
country of domicile of the subscriber. Mobile Network Code consists of two or
three digits and identifies the Home PLMN within a country. For a 2-digit MNC
the total string length of PLMNID is 5.
"
::= { plmnListTableEntry 4 }


plmnListTblCellReservedForOperatorUse  OBJECT-TYPE
SYNTAX                                 BoolType
MAX-ACCESS                             read-write
STATUS                                 current
DESCRIPTION
"
Indicates whether the cell is reserved for operator use or not. If true, it
is reserved. If false, it is not reserved. Corresponds to 'reserved'
'notReserved' respectively as defined in PLMN-IdentityInfo in
[Section 6.2.2/3GPP-TS.36.331].
"
::= { plmnListTableEntry 5 }


qoSTable            OBJECT-TYPE
SYNTAX SEQUENCE OF  QoSTableEntry
MAX-ACCESS          not-accessible
STATUS              current
DESCRIPTION
"
This object contains parameters relating to configuring QoS in LTE EPC.

At most one entry in this table (regardless of whether or not it is enabled)
can exist with a given value for Alias. On creation of a new table entry, the
CPE MUST choose an initial value for Alias such that the new entry does not
conflict with any existing entries.

At most one enabled entry in this table can exist with a given value for QCI.
"
::= { epc 9 }


QoSTableEntry ::= SEQUENCE {
        qoSTblIndex                   Unsigned32,
        qoSTblQCI                     Unsigned32,
        qoSTblType                    DisplayString,
        qoSTblPriority                Unsigned32,
        qoSTblPacketDelayBudget       INTEGER
}


qoSTableEntry              OBJECT-TYPE
SYNTAX                     QoSTableEntry
MAX-ACCESS                 not-accessible
STATUS                     current
DESCRIPTION
"
A row in qoSTable.
"
INDEX { qoSTblIndex }
::= { qoSTable 1 }


qoSTblIndex          OBJECT-TYPE
SYNTAX               Unsigned32
MAX-ACCESS           not-accessible
STATUS               current
DESCRIPTION
"
Index of a row in qoSTable.
"
::= { qoSTableEntry 1 }


qoSTblQCI             OBJECT-TYPE
SYNTAX                Unsigned32(1..20)
MAX-ACCESS            read-only
STATUS                current
DESCRIPTION
"
QoS class identity as defined in [Section 6.1.7.2/3GPP-TS.23.203].
"
DEFVAL { 1 }
::= { qoSTableEntry 2 }


qoSTblType       OBJECT-TYPE
SYNTAX           DisplayString (SIZE(1..64))
MAX-ACCESS       read-only
STATUS           current
DESCRIPTION
"
Defines the type of the QoS class as defined in
[Section 6.1.7.2/3GPP-TS.23.203]. Enumeration of:

  * GBR
  * Non-GBR 
"
DEFVAL { "Non-GBR" }
::= { qoSTableEntry 3 }


qoSTblPriority       OBJECT-TYPE
SYNTAX               Unsigned32(1..20)
MAX-ACCESS           read-only
STATUS               current
DESCRIPTION
"
Priority of the QoS class as defined in [Section 6.1.7.2/3GPP-TS.23.203].
"
DEFVAL { 1 }
::= { qoSTableEntry 4 }


qoSTblPacketDelayBudget   OBJECT-TYPE
SYNTAX                    INTEGER {
                               ms50(50), ms100(100), ms150(150), ms200(200),
                               ms300(300),ms400(400), ms500(500), ms600(600),
                               ms700(700), ms800(800), ms900(900),
                               ms1000(1000), ms1500(1500), ms2000(2000)
                             }
MAX-ACCESS                read-only
STATUS                    current
DESCRIPTION
"
Defines the Packet delay budget, specified in milliseconds, as defined in
[Section 6.1.7.2/3GPP-TS.23.203].
"
DEFVAL { 50 }
::= { qoSTableEntry 5 }


cellIdentity OBJECT-TYPE
SYNTAX       Unsigned32 (0..268435455)
MAX-ACCESS   read-write
STATUS       current
DESCRIPTION
"
Cell Identity as specified in [Section 6.3.4/3GPP-TS.36.331].
"
::= { common 1 }


tRelocPrep      OBJECT-TYPE
SYNTAX          Unsigned32 (0..255)
MAX-ACCESS      read-write
STATUS          current
DESCRIPTION
"
Maximum time for the Handover Preparation procedure in the source LTE device,
specified in seconds, with a numeric range between 0 and 300 inclusive. Only
values in multiple of 5 are valid; use of other values within the defined
range MUST be rejected by the CPE. The value of TRelocPrep divided by 10
yields the actual value. (Ref [Section 6.1.9/3GPP-TS.32.592])

The timer is started when the LTE device sends the HANDOVER REQUIRED message.
Upon reception of the HANDOVER COMMAND message the LTE device shall stop the
timer. Corresponds to parameter TS1RELOCprep defined in
[Section 8.4.1.2/3GPP-TS.36.413].
"
DEFVAL { 1 }
::= { s1AP 1  }


tRelocOverall   OBJECT-TYPE
SYNTAX          Unsigned32 (0..60)
MAX-ACCESS      read-write
STATUS          current
DESCRIPTION
"
Maximum time for the protection of the overall handover procedure in the
source LTE device, specified in seconds, with a numeric range between 0 and 300
inclusive. Only values in multiple of 5 are valid; use of other values within
the defined range MUST be rejected by the CPE. The value of TRelocOverall
divided by 10 yields the actual value. (Ref [Section 6.1.9/3GPP-TS.32.592])

The timer is started with the reception of the HANDOVER COMMAND message.
Corresponds to parameter TS1RELOCOverall defined in
[Section 8.4.1.2/3GPP-TS.36.413].
"
DEFVAL { 1 }
::= { s1AP 2 }



numberOfRaPreambles   OBJECT-TYPE
SYNTAX                INTEGER { n4(4), n8(8), n12(12), n16(16), n20(20),
                                n24(24), n28(28), n32(32), n36(36),
                                n40(40), n44(44), n48(48), n52(52),
                                n56(56), n60(60), n64(64)
                              }
MAX-ACCESS            read-write
STATUS                current
DESCRIPTION
"
Number of non-dedicated random access preambles.

Corresponds to parameter numberOfRA-Preambles specified in
[Section 6.3.2/3GPP-TS.36.331] and in [Section 5.1.1/3GPP-TS.36.321].
"
::= { rach 1  }


sizeOfRaGroupA   OBJECT-TYPE
SYNTAX           INTEGER { n4(4), n8(8), n12(12), n16(16), n20(20),
                           n24(24), n28(28), n32(32), n36(36),
                           n40(40), n44(44), n48(48), n52(52),
                           n56(56), n60(60)
                         }
MAX-ACCESS       read-write
STATUS           current
DESCRIPTION
"
Number of non-dedicated random access preambles in Random Acces Preambles
group A.

Corresponds to parameter sizeOfRA-PreamblesGroupA specified in
[Section 6.3.2/3GPP-TS.36.331] and in [Section 5.1.1/3GPP-TS.36.321].
"
::= { rach 2  }


messageSizeGroupA   OBJECT-TYPE
SYNTAX              INTEGER  { b56(56), b144(144), b208(208), b256(256) }
MAX-ACCESS          read-write
STATUS              current
DESCRIPTION
"
Threshold for preamble selection in bits. Defined in
[Section 5.1.2/3GPP-TS.36.321].

Corresponds to parameter messageSizeGroupA specified in
[Section 6.3.2/3GPP-TS.36.331].
"
::= { rach 3 }


messagePowerOffsetGroupB   OBJECT-TYPE
SYNTAX                     INTEGER { minusinfinity(-1), dB0(0), dB5(5),
                                     dB8(8), dB10(10), dB12(12), dB15(15),
                                     dB18(18)
                                   }
MAX-ACCESS                 read-write
STATUS                     current
DESCRIPTION
"
Threshold for preamble selection, specified in dB. Defined in
[Section 5.1.2/3GPP-TS.36.321].

A value of -1 indicates 'minusinfinity'.

Corresponds to parameter messagePowerOffsetGroupB specified in
[Section 6.3.2/3GPP-TS.36.331].
"
::= { rach 4  }


powerRampingStep   OBJECT-TYPE
SYNTAX             INTEGER { dB0(0), dB2(2), dB4(4), dB6(6) }
MAX-ACCESS         read-write
STATUS             current
DESCRIPTION
"
Power increase factor between subsequent random access preamble
transmissions, specified in dB.

Corresponds to parameter powerRampingStep specified in
[Section 6.3.2/3GPP-TS.36.331] and in [Section 5.1.3/3GPP-TS.36.321].
"
::= { rach 5  }


preambleInitialReceivedTargetPower   OBJECT-TYPE
SYNTAX                               INTEGER { dBmMinus120(-120),
                                               dBmMinus118(-118),
                                               dBmMinus116(-116),
                                               dBmMinus114(-114),
                                               dBmMinus112(-112),
                                               dBmMinus110(-110),
                                               dBmMinus108(-108),
                                               dBmMinus106(-106),
                                               dBmMinus104(-104),
                                               dBmMinus102(-102),
                                               dBmMinus100(-100),
                                               dBmMinus98(-98),
                                               dBmMinus96(-96),
                                               dBmMinus94(-94),
                                               dBmMinus92(-92),
                                               dBmMinus90(-90)
                                             }
MAX-ACCESS                           read-write
STATUS                               current
DESCRIPTION
"
Value used as the baseline for computation for random access transmission
power, specified in dBm. Also used as a parameter in the criteria for
preamble selection.

Corresponds to parameter preambleInitialReceivedTargetPower specified in
[Section 6.3.2/3GPP-TS.36.331] and in [Section 5.1.2/3GPP-TS.36.321]. and
section 5.1.3.
"
::= { rach 6  }


preambleTransMax  OBJECT-TYPE
SYNTAX            INTEGER { n3(3), n4(4), n5(5),
                            n6(6), n7(7), n8(8),
                            n10(10), n20(20), n50(50),
                            n100(100), n200(200)
                          }
MAX-ACCESS        read-write
STATUS            current
DESCRIPTION
"
Maximum number of random access preamble transmissions.

Corresponds to parameter preambleTransMax specified in
[Section 6.3.2/3GPP-TS.36.331] and in
[Section 5.1.4 and section 5.1.5/3GPP-TS.36.321].
"
::= { rach 7  }


responseWindowSize   OBJECT-TYPE
SYNTAX               INTEGER { sf2(2), sf3(3), sf4(4), sf5(5),
                               sf6(6), sf7(7), sf8(8), sf10(10)
                             }
MAX-ACCESS           read-write
STATUS               current
DESCRIPTION
"
The value is a duration of the random access response window, specified in
subframes.

Corresponds to parameter ra-ResponseWindowSize specified in
[Section 6.3.2/3GPP-TS.36.331] and in [Section 5.1.4/3GPP-TS.36.321].
"
::= { rach 8  }


contentionResolutionTimer   OBJECT-TYPE
SYNTAX                      INTEGER { sf8(8), sf16(16), sf24(24),
                                      sf32(32), sf40(40), sf48(48),
                                      sf56(56), sf64(64)
                                    }
MAX-ACCESS                  read-write
STATUS                      current
DESCRIPTION
"
Contention resolution timer, specified in subframes.

Corresponds to parameter mac-ContentionResolutionTimer specified in
[Section 6.3.2/3GPP-TS.36.331] and in [Section 5.1.5/3GPP-TS.36.321].
"
::= { rach 9  }


maxHARQMsg3Tx   OBJECT-TYPE
SYNTAX          Unsigned32 (1..8)
MAX-ACCESS      read-write
STATUS          current
DESCRIPTION
"
Maximum number of Msg3 HARQ transmissions by RRC.

Corresponds to parameter maxHARQ-Msg3Tx specified in
[Section 6.3.2/3GPP-TS.36.331] and in [Section 5.4.2.2/3GPP-TS.36.321].
"
::= { rach 10  }



drxEnabled   OBJECT-TYPE
SYNTAX       BoolType 
MAX-ACCESS   read-write
STATUS       current
DESCRIPTION
"
Specifies whether DRX operation is enabled or not. If true, DRX operation is
enabled. If false, DRX operation is not enabled.

Corresponds to drx-Configuration IE defined in [Section 6.3.2/3GPP-TS.36.331].
"
::= { drx  1  }


onDurationTimer  OBJECT-TYPE
SYNTAX           INTEGER { psf1(1), psf2(2), psf3(3), psf4(4), psf5(5),
                           psf6(6), psf8(8), psf10(10), psf20(20), psf30(30),
                           psf40(40), psf50(50), psf60(60), psf80(80),
                           psf100(100), psf200(200)
                         }
MAX-ACCESS       read-write
STATUS           current
DESCRIPTION
"
DRX cycle during which UE actively monitors PDCCH, specified in number PDCCH
subframes.

Corresponds to parameter onDurationTimer specified in
[Section 6.3.2/3GPP-TS.36.331] and in [Section 5.7/3GPP-TS.36.321].
"
::= { drx  2  }


drxInactivityTimer   OBJECT-TYPE
SYNTAX               INTEGER { psf1(1), psf2(2), psf3(3), psf4(4), psf5(5),
                               psf6(6), psf8(8), psf10(10), psf20(20),
                               psf30(30), psf40(40), psf50(50), psf60(60),
                               psf80(80), psf100(100), psf200(200),
                               psf300(300), psf500(500), psf750(750),
                               psf1280(1280), psf1920(1920), psf2560(2560)
                             }

MAX-ACCESS           read-write
STATUS               current
DESCRIPTION
"
Defines the number of inactive consecutive PDCCH sub-frame(s) that will
activate short DRX cycle, specified in number of PDCCH subframes.

Corresponds to parameter drx-InactivityTimer specified in
[Section 6.3.2/3GPP-TS.36.331] and in [Section 5.7/3GPP-TS.36.321].
"
::= { drx  3  }


drxRetransmissionTimer  OBJECT-TYPE
SYNTAX                  INTEGER { psf1(1), psf2(2), psf4(4), psf6(6),
                                  psf8(8), psf16(16), psf24(24), psf33(33)
                                }
MAX-ACCESS              read-write
STATUS                  current
DESCRIPTION
"
Maximum number of consecutive PDCCH sub-frame(s) UE MUST remain active
expecting a DL retransmission, specified in number of PDCCH subframes. The
timer is started when a HARQ RTT Timer expires and the data in the soft
buffer of the corresponding HARQ process was not successfully decoded. There
is one timer for each active HARQ process.

Corresponds to parameter drx-RetransmissionTimer specified in
[Section 6.3.2/3GPP-TS.36.331] and in [Section 5.7/3GPP-TS.36.321].
"
::= { drx  4  }


longDRXCycle   OBJECT-TYPE
SYNTAX         INTEGER { sf10(10), sf20(20), sf32(32), sf40(40), sf64(64),
                         sf80(80), sf128(128), sf160(160), sf256(256),
                         sf320(320), sf512(512), sf640(640), sf1024(1024),
                         sf1280(1280), sf2048(2048), sf2560(2560)
                       }
MAX-ACCESS     read-write
STATUS         current
DESCRIPTION
"
Long DRX Cycle value, specified in number of subframes. If shortDRX-Cycle is
configured, this value MUST be a multiple of the ShortDRXCycle value.

Corresponds to longDRX-Cycle parameter specified in
[Section 5.7/3GPP-TS.36.321] and longDRX-CycleStartOffset specified in
[Section 6.3.2/3GPP-TS.36.331].
"
::= { drx  5  }


drxStartOffset   OBJECT-TYPE
SYNTAX           Unsigned32 (0..2559)
MAX-ACCESS       read-write
STATUS           current
DESCRIPTION
"
Defines the starting frame of the DRX cycle within the long DRX cycle. The
valid value range is dependent on LongDRXCycle parameter which defines the
upper bound of this range, i.e., range definition is [0: (LongDRXCycle-1)].

Use of values bigger than (LongDRXCycle-1) MUST be rejected by the CPE.

Corresponds to drxStartOffset parameter specified in
[Section 5.7/3GPP-TS.36.321].
"
::= { drx  6  }


shortDRXCycle  OBJECT-TYPE
SYNTAX         INTEGER { sf2(2), sf5(5), sf8(8), sf10(10), sf16(16),
                         sf20(20), sf32(32), sf40(40), sf64(64),
                         sf80(80), sf128(128), sf160(160), sf256(256),
                         sf320(320), sf512(512), sf640(640)
                       }
MAX-ACCESS     read-write
STATUS         current
DESCRIPTION
"
Short DRX Cycle value, specified in number of subframes. If shortDRX-Cycle
is configured, the value of LongDRXCycle MUST be a multiple of the
ShortDRXCycle value.

Corresponds to shortDRX-Cycle parameter specified in
[Section 5.7/3GPP-TS.36.321].
"
::= { drx  7 }


drxShortCycleTimer   OBJECT-TYPE
SYNTAX               Unsigned32 (1..16)
MAX-ACCESS           read-write
STATUS               current
DESCRIPTION
"
Duration of the short DRX cycle in multiples of ShortDRXCycle parameter,
specified in number of subframes. Denotes the number of consecutive
sub-frame(s)the UE shall follow the short DRX cycle after the DRX Inactivity
Timer has expired.

Corresponds to drxShortCycleTimer parameter specified in
[Section 5.7/3GPP-TS.36.321].
"
::= { drx  8  }


srb1DefaultConfiguration   OBJECT-TYPE
SYNTAX                     BoolType 
MAX-ACCESS                 read-write
STATUS                     current
DESCRIPTION
"
Indicates the whether default RLC configuration for SRB1 is used or not.

If true, the default RLC configuration is used as specified in
[Section 9.2.1.1/3GPP-TS.36.331]. In this case, rest of the parameters
defined under the current object are ignored by the CPE.

If false, rest of the parameters defined under the current object are used by
the CPE for RLC configuration.
"
::= { srb1 1  }

srb1TPollRetransmit   OBJECT-TYPE
SYNTAX                TPollRetransmitType
MAX-ACCESS            read-write
STATUS                current
DESCRIPTION
"
Comma-separated list (maximum length 256) (at least 1 items) of strings. Each
item is a timer between successive poll transmissions, specified in
milliseconds, specified in milliseconds, with a numeric range between 5 and
500 inclusive. Only the multiple of 5 are valid in the range between 5 and
250 inclusive (i.e. 5, 10, 15, 20,... 250), and only the multiple of 50 are
valid in the range between 300 and 500 inclusive (i.e., 300, 350, 400, 450,
500). If the value is other than these, the CPE MUST reject the value. In
case there is more than one item in the list, the first item contains the
most preferred value.

This parameter is valid only if DefaultConfiguration paramter under the
current object is set to false. Corresponds to t-PollRetransmit IE specified
in [Section 6.3.2/3GPP-TS.36.331] and in [Section 5.2.2/3GPP-TS.36.322].

The multiplicity of the TPollRetransmit values can also be expressed by
defining a range using '..' (two periods) between two values. In this case,
the combination of two values defines the lower-bound and upper-bound of the
range inclusive. If this notation is used, then the list contains at least 2
items: '<preferred-value>,<lower-bound>..<upper-bound>'.

If supports self-configuration capability for TPollRetransmit and more than
one item is configured, then is expected to select one from the list and
overwrite this parameter containing only the one selected. If does not
support self-configuration capability for TPollRetransmit and more than one
item is configured, then accepts the first value and ignore the rest. If only
one item is configured regardless of the self-configuration capability of ,
accepts the value as an explicit configuration by the ACS.
"
::= { srb1 2  }

srb1PollPDU   OBJECT-TYPE
SYNTAX        PollPDUType
MAX-ACCESS    read-write
STATUS        current
DESCRIPTION
"
Counter of PDUs between successive poll transmissions, specified in number of
PDUs. Value of 0 indicates infinite amount of number of PDUs. This parameter
is valid only if DefaultConfiguration parameter under the current object is
set to false.

Corresponds to pollPDU IE specified in [Section 6.3.2/3GPP-TS.36.331] and in
[Section 5.2.2.1/3GPP-TS.36.322].
"
::= { srb1 3  }


srb1PollByte   OBJECT-TYPE
SYNTAX         PollByteType
MAX-ACCESS     read-write
STATUS         current
DESCRIPTION
"
Counter of PDU bytes transmitted between successive poll transmissions,
specified in kBytes. Value of 0 indicates infinite amount of kBytes. This
parameter is valid only if DefaultConfiguration parameter under the current
object is set to false.
"
::= { srb1 4  }


srb1MaxRetxThreshold   OBJECT-TYPE
SYNTAX                 MaxRetxThresholdType
MAX-ACCESS             read-write
STATUS                 current
DESCRIPTION
"
Maximum number of transmission retry used by the RLC entity to limit the
number of retransmissions of an AMD PDU. This parameter is valid only if
DefaultConfiguration paramter under the current object is set to false.
"
::= { srb1 5  }


srb1TReordering   OBJECT-TYPE
SYNTAX            TReorderingType
MAX-ACCESS        read-write
STATUS            current
DESCRIPTION
"
Timer used by the receiving side of an RLC entity in order to detect loss of
RLC PDUs at lower layer, specified in milliseconds. A value of 0 means the
timer is not used. This parameter is valid only if DefaultConfiguration
parameter under the current object is set to false.
"
::= { srb1 6 }


srb1TStatusProhibit  OBJECT-TYPE
SYNTAX              TStatusProhibitType
MAX-ACCESS          read-write
STATUS              current
DESCRIPTION
"
Timer used by the receiving side of an AM RLC entity in order to prohibit
transmission of a STATUS PDU, specified in milliseconds. A value of 0 means
the timer is not used. This parameter is valid only if DefaultConfiguration
parameter under the current object is set to false.
"
::= { srb1 7 }


srb2DefaultConfiguration   OBJECT-TYPE
SYNTAX                     BoolType 
MAX-ACCESS                 read-write
STATUS                     current
DESCRIPTION
"
Indicates the whether default RLC configuration for SRB1 is used or not.
"
::= { srb2 1  }


srb2TPollRetransmit   OBJECT-TYPE
SYNTAX                TPollRetransmitType
MAX-ACCESS            read-write
STATUS                current
DESCRIPTION
"
Timer between successive poll transmissions, specified in milliseconds. This
parameter is valid only if DefaultConfiguration parameter under the current
object is set to false.
"
::= { srb2 2  }


srb2PollPDU   OBJECT-TYPE
SYNTAX        PollPDUType
MAX-ACCESS    read-write
STATUS        current
DESCRIPTION
"
Counter of PDUs between successive poll transmissions, specified in number of
PDUs. Value of 0 indicates infinite amount of number of PDUs. This parameter
is valid only if DefaultConfiguration parameter under the current object is
set to false.
"
::= { srb2 3  }


srb2PollByte   OBJECT-TYPE
SYNTAX         PollByteType
MAX-ACCESS     read-write
STATUS         current
DESCRIPTION
"
Counter of PDU bytes transmitted between successive poll transmissions,
specified in kBytes. Value of 0 indicates infinite amount of kBytes. This
parameter is valid only if DefaultConfiguration parameter under the current
object is set to false.
"
::= { srb2 4  }


srb2MaxRetxThreshold   OBJECT-TYPE
SYNTAX                 MaxRetxThresholdType
MAX-ACCESS             read-write
STATUS                 current
DESCRIPTION
"
Maximum number of transmission retry used by the RLC entity to limit the
number of retransmissions of an AMD PDU. This parameter is valid only if
DefaultConfiguration paramter under the current object is set to false.
"
::= { srb2 5  }


srb2TReordering   OBJECT-TYPE
SYNTAX            TReorderingType
MAX-ACCESS        read-write
STATUS            current
DESCRIPTION
"
Timer used by the receiving side of an RLC entity in order to detect loss of
RLC PDUs at lower layer, specified in milliseconds. A value of 0 means the
timer is not used. This parameter is valid only if DefaultConfiguration
parameter under the current object is set to false.
"
::= { srb2 6  }


srb2TStatusProhibit  OBJECT-TYPE
SYNTAX               TStatusProhibitType
MAX-ACCESS           read-write
STATUS               current
DESCRIPTION
"
Timer used by the receiving side of an AM RLC entity in order to prohibit
transmission of a STATUS PDU, specified in milliseconds. A value of 0 means
the timer is not used. This parameter is valid only if DefaultConfiguration
parameter under the current object is set to false.
"
::= { srb2 7 }


t300        OBJECT-TYPE
SYNTAX      TimerType1
MAX-ACCESS  read-write
STATUS      current
DESCRIPTION
"
Interval in milliseconds between subsequent transmissions of
RRCConnectionRequest. 
"
::= { rrcTimers 1  }


t301        OBJECT-TYPE
SYNTAX      TimerType1
MAX-ACCESS  read-write
STATUS      current
DESCRIPTION
"
Interval in milliseconds between subsequent transmissions of
RRCConnectionReestablishmentRequest. 
"
::= { rrcTimers 2  }




t302        OBJECT-TYPE
SYNTAX      TimerType1
MAX-ACCESS  read-write
STATUS      current
DESCRIPTION
"
Time to wait in milliseconds for cell re-selection or RRConnectionSetup after
RRCConnectionReject.
"
::= { rrcTimers 3  }


t304EUTRA   OBJECT-TYPE
SYNTAX      T304EUTRAType
MAX-ACCESS  read-write
STATUS      current
DESCRIPTION
"
HO failure timer in milliseconds.
"
::= { rrcTimers 4  }


t304IRAT   OBJECT-TYPE
SYNTAX     T304IRATType
MAX-ACCESS read-write
STATUS     current
DESCRIPTION
"
HO failure timer in milliseconds.
"
::= { rrcTimers 5  }


t310        OBJECT-TYPE
SYNTAX      T310Type
MAX-ACCESS  read-write
STATUS      current
DESCRIPTION
"
RLF declaration timer in milliseconds. 
"
::= { rrcTimers 6  }


t311            OBJECT-TYPE
SYNTAX          T311Type
MAX-ACCESS      read-write
STATUS          current
DESCRIPTION
"
RLF recovery timer in milliseconds.
"
::= { rrcTimers 7  }


t320            OBJECT-TYPE
SYNTAX          T320Type
MAX-ACCESS      read-write
STATUS          current
DESCRIPTION
"
Time in minutes after RRCConnection Release in which cell re-selection
priority info supplied in RRCConnectionRelease MUST be observed.
"
::= { rrcTimers 8  }


n310        OBJECT-TYPE
SYNTAX      N310Type
MAX-ACCESS  read-write
STATUS      current
DESCRIPTION
"
Number of consecutive 'out-of-sync' indications received from lower layers
that triggers timer T310.
"
::= { rrcTimers 9  }



n311            OBJECT-TYPE
SYNTAX          N311Type
MAX-ACCESS      read-write
STATUS          current
DESCRIPTION
"
Number of consecutive 'in-sync' indications received from lower layers that
stops timer T310.
"
::= { rrcTimers 10  }


cellBarred      OBJECT-TYPE
SYNTAX          BoolType
MAX-ACCESS      read-only
STATUS          current
DESCRIPTION
"
Indicates whether the is barred or not. If true, the cell is barred. If
false, the cell is not barred.
"
::= { cellRestriction 1 }


cellRestrictionCellReservedForOperatorUse   OBJECT-TYPE
SYNTAX                                      BoolType
MAX-ACCESS                                  read-only
STATUS                                      current
DESCRIPTION
"
Indicates whether the is reserved for operator's use or not. If true, the
cell is reserved for operator use. If false, the cell is not reserved for
operator use.
"
::= { cellRestriction 2  }


barringForEmergency   OBJECT-TYPE
SYNTAX                BoolType
MAX-ACCESS            read-only
STATUS                current
DESCRIPTION
"
Indicates whether the is barred for Access Class 10 or not.

If true, the cell is barred for Access Class 10.

If false, the cell is not barred for Access Class 10.
"
::= { cellRestriction 3  }


qHyst       OBJECT-TYPE
SYNTAX      QHystType
MAX-ACCESS  read-only
STATUS      current
DESCRIPTION
"
Hysteresis value applied to serving cell for evaluating cell ranking criteria
specified in dB.
"
::= { idleModeCommon 1 }




qHystSFMedium   OBJECT-TYPE
SYNTAX          QHystSFType
MAX-ACCESS      read-only
STATUS          current
DESCRIPTION
"
Speed-dependent scaling factor for Qhyst in Medium-mobility state, specified
in dB.
"
::= { idleModeCommon 2 }



qHystSFHigh     OBJECT-TYPE
SYNTAX          QHystSFType
MAX-ACCESS      read-only
STATUS          current
DESCRIPTION
"
Speed-dependent scaling factor for Qhyst in High-mobility state, specified
in dB.
"
::= { idleModeCommon 3 }


tEvaluation     OBJECT-TYPE
SYNTAX          TEvaluationType
MAX-ACCESS      read-only
STATUS          current
DESCRIPTION
"
Duration for evaluating allowed amount of cell re-selection(s) required to
enter mobility states, specified in seconds.
"
::= { idleModeCommon 4 }


tHystNormal     OBJECT-TYPE
SYNTAX          TEvaluationType
MAX-ACCESS      read-only
STATUS          current
DESCRIPTION
"
Additional duration for evaluating criteria to enter normal mobility state,
specified in seconds. Specifies the additional time period for evaluating
criteria to enter Normal-mobility state.
"
::= { idleModeCommon 5 }


nCellChangeMedium OBJECT-TYPE
SYNTAX            Unsigned32  (1..16)
MAX-ACCESS        read-only
STATUS            current
DESCRIPTION
"
Defines the number of cell re-selections within TEvaluation to enter
Medium-mobility state.
"
::= { idleModeCommon 6 }


nCellChangeHigh OBJECT-TYPE
SYNTAX          Unsigned32  (1..16)
MAX-ACCESS      read-only
STATUS          current
DESCRIPTION
"
Defines the number of cell re-selections within TEvaluation to enter
High-mobility state.
"
::= { idleModeCommon 7 }


qRxLevMinSIB1       OBJECT-TYPE
SYNTAX              Integer32 (-70..-22)
MAX-ACCESS          read-only
STATUS              current
DESCRIPTION
"
REQUIRED minimum received RSRP level of a E-UTRA cell for cell selection,
specified in dBm. The value of (QRxLevMinSIB1 * 2) yields the actual value
"
::= { intraFreq 1 }


qRxLevMinSIB3  OBJECT-TYPE
SYNTAX         Integer32 (-70..-22)
MAX-ACCESS     read-only
STATUS         current
DESCRIPTION
"
REQUIRED minimum received RSRP level for intra-frequency E-UTRA cell
re-selection, specified idBm. The value of (QRxLevMinSIB3 * 2) yields the
actual value
"
::= { intraFreq 2 }


qRxLevMinOffset    OBJECT-TYPE
SYNTAX             Unsigned32  (1..8)
MAX-ACCESS         read-only
STATUS             current
DESCRIPTION
"
Defines offset with respect to QrxLevMin, specified in dBm. This offset is
taken into account in the computation of Srxlev for cell selection
evaluation of cells detected during a periodic search for a higher priority
PLMN while camped normally in a VPLMN. The value of (QRxLevMinOffset * 2)
yields the actual value.
"
::= { intraFreq 3}


sIntraSearch   OBJECT-TYPE
SYNTAX         Unsigned32 (0..31)
MAX-ACCESS     read-only
STATUS         current
DESCRIPTION
"
Threshold for intra-frequency measurements, specified in dB. The value of
(SIntraSearch * 2) yields the actual value.
"
::= { intraFreq 4 }


idleModeIntraFreqTReselectionEUTRA  OBJECT-TYPE
SYNTAX                              Unsigned32 (0..7)
MAX-ACCESS                          read-only
STATUS                              current
DESCRIPTION
"
Cell re-selection timer for intra-frequency E-UTRA cell re-selection,
specified in seconds.
"
::= { intraFreq 5 }


sNonIntraSearch    OBJECT-TYPE
SYNTAX             Unsigned32 (0..31)
MAX-ACCESS         read-only
STATUS             current
DESCRIPTION
"
Threshold for inter-frequency and inter-RAT measurements with lower or equal
priority, specified in dB. The value of (SNonIntraSearch * 2) yields the
actual value.
"
::= { intraFreq 6 }


idleModeIntraFreqCellReselectionPriority    OBJECT-TYPE
SYNTAX                                      Unsigned32  (0..7)
MAX-ACCESS                                  read-only
STATUS                                      current
DESCRIPTION
"
Absolute priority of the E-UTRAN serving carrier frequency used in the
inter-frequency and inter-RAT cell re-selection procedure.
"
::= { intraFreq 7 }


threshServingLow   OBJECT-TYPE
SYNTAX             Unsigned32 (0..31)
MAX-ACCESS         read-only
STATUS             current
DESCRIPTION
"
Threshold for serving frequency used in evaluation of re-selection towards
lower priority E-UTRAN frequency or inter-RAT, specified in dB. The value of
(ThreshServingLow * 2) yields the actual value.
"
::= { intraFreq 8 }



intraFreqTReselectionEUTRASFMedium    OBJECT-TYPE
SYNTAX                                TReselectionSFType
MAX-ACCESS                            read-only
STATUS                                current
DESCRIPTION
"
Scaling factor for intra-frequency TreselectionEUTRA in Medium-mobility
state. The value of TReselectionEUTRASFMedium divided by 100 yields the
actual SF value.
"
::= { intraFreq 9 }


intraFreqTReselectionEUTRASFHigh    OBJECT-TYPE
SYNTAX                              TReselectionSFType
MAX-ACCESS                          read-only
STATUS                              current
DESCRIPTION
"
Scaling factor for intra-frequency TreselectionEUTRA in High-mobility state.
The value of TReselectionEUTRASFHigh divided by 100 yields the actual SF
value.
"
::= { intraFreq 10 }


maxCarrierEntries      OBJECT-TYPE
SYNTAX                 Unsigned32 
MAX-ACCESS             read-only
STATUS                 current
DESCRIPTION
"
The maximum number of entries in the
CellConfig.LTE.RAN.Mobility.IdleMode.InterFreq.Carrier.{i}. table.
"
::= { interFreq 1 }


carrierNumberOfEntries          OBJECT-TYPE
SYNTAX                          Unsigned32 
MAX-ACCESS                      read-only
STATUS                          current
DESCRIPTION
"
The number of entries in the Carrier table.
"
::= { interFreq 2 }


carrierTable            OBJECT-TYPE
SYNTAX SEQUENCE OF      CarrierTableEntry
MAX-ACCESS              not-accessible
STATUS                  current
DESCRIPTION
"
This object contains parameters relating to the carrier information for
inter-freq re-selection scenario.
"
::= { interFreq 3 }

CarrierTableEntry  ::= SEQUENCE {
        carrierTblIndex                              Unsigned32,
        carrierTblEUTRACarrierARFCN                  Unsigned32,
        carrierTblQOffsetFreq                        INTEGER,
        carrierTblQRxLevMinSIB5                      Integer32,
        carrierTblPMax                               Integer32,
        carrierTblTReselectionEUTRA                  Unsigned32,
        carrierTblTReselectionEUTRASFMedium          TReselectionSFType,
        carrierTblTReselectionEUTRASFHigh            TReselectionSFType,
        carrierTblThreshXHigh                        Unsigned32,
        carrierTblThreshXLow                         Unsigned32,
        carrierTblCellReselectionPriority            Unsigned32
    }


carrierTableEntry        OBJECT-TYPE
SYNTAX                   CarrierTableEntry
MAX-ACCESS               not-accessible
STATUS                   current
DESCRIPTION
"
A row entry in carrierTable
carrierTblEUTRACarrierARFCN is the key element of each row
"
INDEX { carrierTblIndex }
::= { carrierTable 1 }


carrierTblIndex OBJECT-TYPE
SYNTAX          Unsigned32
MAX-ACCESS      not-accessible
STATUS          current
DESCRIPTION
"
Unique index identifying a row in carrierTable
"
::= { carrierTableEntry 1 }


carrierTblEUTRACarrierARFCN    OBJECT-TYPE
SYNTAX                         Unsigned32 (0..65535)
MAX-ACCESS                     read-write
STATUS                         current
DESCRIPTION
"
Indicates the ARFCN of this frequency carrier.
Note : carrierTblEUTRACarrierARFCN is key element for each row 
 hence SET for carrierTblEUTRACarrierARFCN parameter is not supoorted.
"
::= { carrierTableEntry 2 }


carrierTblQOffsetFreq     OBJECT-TYPE
SYNTAX                    QOffsetType
MAX-ACCESS                read-write
STATUS                    current
DESCRIPTION
"
Offset applicable between serving and this frequency carrier, specified in
dB. The value of (QOffsetFreq * 2) yields the actual value.
"
::= { carrierTableEntry 3 }


carrierTblQRxLevMinSIB5       OBJECT-TYPE
SYNTAX                        Integer32 (-70..-22)
MAX-ACCESS                    read-write
STATUS                        current
DESCRIPTION
"
REQUIRED minimum received RSRP level on this E-UTRA frequency carrier,
spcified in dBm. The value of (QRxLevMinSIB5 * 2) yields the actual value.
"
::= { carrierTableEntry 4 }


carrierTblPMax             OBJECT-TYPE
SYNTAX                     Integer32 (-30..33)
MAX-ACCESS                 read-write
STATUS                     current
DESCRIPTION
"
Used to limit the allowed UE uplink transmission power on this carrier
frequency, specified in dBm.
"
::= { carrierTableEntry 5 }


carrierTblTReselectionEUTRA    OBJECT-TYPE
SYNTAX                         Unsigned32 (0..8)
MAX-ACCESS                     read-write
STATUS                         current
DESCRIPTION
"
Cell re-selection timer for inter-frequency cell re-selection to this E-UTRA
frequency carrier, specified in seconds.
"
::= { carrierTableEntry 6 }



carrierTblTReselectionEUTRASFMedium    OBJECT-TYPE
SYNTAX                                 TReselectionSFType
MAX-ACCESS                             read-write
STATUS                                 current
DESCRIPTION
"
Scaling factor for TreselectionEUTRA for inter-frequency re-selection to this
frequency carrier in Medium-mobility state. The value of
TReselectionEUTRASFMedium divided by 100 yields the actual SF value.
"
::= { carrierTableEntry 7 }


carrierTblTReselectionEUTRASFHigh      OBJECT-TYPE
SYNTAX                                 TReselectionSFType
MAX-ACCESS                             read-write
STATUS                                 current
DESCRIPTION
"
Scaling factor for TreselectionEUTRA for inter-frequency re-selection to this
frequency carrier in High-mobility state. The value of
TReselectionEUTRASFHigh divided by 100 yields the actual SF value.
"
::= { carrierTableEntry 8 }


carrierTblThreshXHigh          OBJECT-TYPE
SYNTAX                         Unsigned32 (0..31)
MAX-ACCESS                     read-write
STATUS                         current
DESCRIPTION
"
Threshold used when re-selecting from a lower priority E-UTRAN frequency,
specified in dB. The value of (ThreshXHigh * 2) yields the actual value.
"
::= { carrierTableEntry 9 }


carrierTblThreshXLow   OBJECT-TYPE
SYNTAX                 Unsigned32 (0..31)
MAX-ACCESS             read-write
STATUS                 current
DESCRIPTION
"
Threshold used when re-selecting from a higher priority E-UTRAN frequency,
specified in dB. The value of (ThreshXLow * 2) yields the actual value.
"
::= {  carrierTableEntry 10 }


carrierTblCellReselectionPriority      OBJECT-TYPE
SYNTAX                                 Unsigned32 (0..7)
MAX-ACCESS                             read-write
STATUS                                 current
DESCRIPTION
"
Absolute priority of this E-UTRA frequency carrier, as used by the
inter-frequency cell re-selection procedure.
"
::= { carrierTableEntry 11 }



tReselectionUTRA        OBJECT-TYPE
SYNTAX                  Unsigned32 (0..7)
MAX-ACCESS              read-write
STATUS                  current
DESCRIPTION
"
Cell re-selection timer for re-selection to a UTRA frequency carrier,
specified in seconds.
"
::= { utra 1 }


tReselectionUTRASFMedium    OBJECT-TYPE
SYNTAX                      TReselectionSFType
MAX-ACCESS                  read-write
STATUS                      current
DESCRIPTION
"
Scaling factor for TreselectionUTRA for inter-RAT re-selection to UTRA in
Medium-mobility state. The value of TReselectionUTRASFMedium divided by 100
yields the actual SF value.
"
::= { utra 2 }


tReselectionUTRASFHigh  OBJECT-TYPE
SYNTAX                  TReselectionSFType
MAX-ACCESS              read-write
STATUS                  current
DESCRIPTION
"
Scaling factor for TreselectionEUTRA for inter-frequency re-selection to this
frequency carrier in High-mobility state. The value of TReselectionUTRASFHigh
divided by 100 yields the actual SF value.
"
::= { utra 3 }


utranFDDFreqNumberOfEntries OBJECT-TYPE
SYNTAX                      Unsigned32
MAX-ACCESS                  read-only
STATUS                      current
DESCRIPTION
"
The number of entries in the utranFDDFreqTable.
"
::= { utra 4 }



utranFDDFreqTable         OBJECT-TYPE
SYNTAX SEQUENCE OF        UTRANFDDFreqTableEntry
MAX-ACCESS                not-accessible
STATUS                    current
DESCRIPTION
"
This object contains parameters relating to the channel frequncy related
information of UTRA (UMTS) system.
"
::= { utra 5 }


UTRANFDDFreqTableEntry  ::= SEQUENCE {
        utranFDDFreqTblIndex                    Unsigned32,
        utranFDDFreqTblUTRACarrierARFCN         Unsigned32,
        utranFDDFreqTblQRxLevMin                Integer32,
        utranFDDFreqTblQQualMin                 Integer32,
        utranFDDFreqTblCellReselectionPriority  Unsigned32,
        utranFDDFreqTblThreshXHigh              Unsigned32,
        utranFDDFreqTblThreshXLow               Unsigned32,
        utranFDDFreqTblPMaxUTRA                 Integer32
    }


utranFDDFreqTableEntry        OBJECT-TYPE
SYNTAX                        UTRANFDDFreqTableEntry
MAX-ACCESS                    not-accessible
STATUS                        current
DESCRIPTION
"
A row entry in utranFDDFreqTable.
utranFDDFreqTblUTRACarrierARFCN is the key element of each row
"
INDEX { utranFDDFreqTblIndex }
::= { utranFDDFreqTable 1 }



utranFDDFreqTblIndex OBJECT-TYPE
SYNTAX               Unsigned32
MAX-ACCESS           not-accessible
STATUS               current
DESCRIPTION
"
A unique index value identifying a row in utranFDDFreqTable.
"
::= { utranFDDFreqTableEntry 1 }



utranFDDFreqTblUTRACarrierARFCN    OBJECT-TYPE
SYNTAX                             Unsigned32 (0..16383)
MAX-ACCESS                         read-write
STATUS                             current
DESCRIPTION
"
Indicates the ARFCN of the frequency carrier.
Note : utranFDDFreqTblUTRACarrierARFCN is key element of each row  
hence SET for utranFDDFreqTblUTRACarrierARFCN parameter is not supoorted.
"
::= { utranFDDFreqTableEntry 2 }



utranFDDFreqTblQRxLevMin   OBJECT-TYPE
SYNTAX                     Integer32 (-60..-13)
MAX-ACCESS                 read-write
STATUS                     current
DESCRIPTION
"
REQUIRED minimum received RSCP level on this UTRA frequency carrier,
specified in dBm. The value of (QRxLevMin * 2 + 1) yields the actual value.
"
::= { utranFDDFreqTableEntry 3 }



utranFDDFreqTblQQualMin        OBJECT-TYPE
SYNTAX                         Integer32 (-24..0)
MAX-ACCESS                     read-write
STATUS                         current
DESCRIPTION
"
REQUIRED minimum received Ec/Io level on this UTRA FDD carrier,
specified in dB
"
::= { utranFDDFreqTableEntry 4 }


utranFDDFreqTblCellReselectionPriority  OBJECT-TYPE
SYNTAX                                  Unsigned32 (0..7)
MAX-ACCESS                              read-write
STATUS                                  current
DESCRIPTION
"
Absolute priority of this UTRA FDD frequency carrier, as used by the
inter-frequency cell re-selection procedure.
"
::= { utranFDDFreqTableEntry 5 }


utranFDDFreqTblThreshXHigh      OBJECT-TYPE
SYNTAX                          Unsigned32 (0..31)
MAX-ACCESS                      read-write
STATUS                          current
DESCRIPTION
"
Threshold used when re-selecting towards a higher priority UTRA FDD
frequency, specified in dB. The value of (ThreshXHigh * 2) yields the
actual value.
"
::= { utranFDDFreqTableEntry 6 }


utranFDDFreqTblThreshXLow   OBJECT-TYPE
SYNTAX                      Unsigned32 (0..31)
MAX-ACCESS                  read-write
STATUS                      current
DESCRIPTION
"
Threshold used when re-selecting towards a lower priority UTRA FDD frequency,
specified in dB. The value of (ThreshXLow * 2) yields the actual value.
"
::= { utranFDDFreqTableEntry 7 }



utranFDDFreqTblPMaxUTRA            OBJECT-TYPE
SYNTAX                             Integer32 (-50..33)
MAX-ACCESS                         read-write
STATUS                             current
DESCRIPTION
"
Used to limit the allowed UE uplink transmission power on this UTRA FDD
carrier frequency, specified in dBm.
"
::= { utranFDDFreqTableEntry 8 }



geranFreqGroupTable       OBJECT-TYPE
SYNTAX SEQUENCE OF        GERANFreqGroupTableEntry
MAX-ACCESS                not-accessible
STATUS                    current
DESCRIPTION
"
This object contains parameters relating to the channel frequncy related
information of GERAN (GSM) system (see [Section 6.1.5.1.7/3GPP-TS.32.592]).
"
::= { geran 1 }


GERANFreqGroupTableEntry  ::= SEQUENCE {
        geranFreqGroupTblIndex                       Unsigned32,
        geranFreqGroupTblQRxLevMin                   Unsigned32,
        geranFreqGroupTblCellReselectionPriority     Unsigned32,
        geranFreqGroupTblThreshXHigh                 Unsigned32,
        geranFreqGroupTblThreshXLow                  Unsigned32
}



geranFreqGroupTableEntry        OBJECT-TYPE
SYNTAX                          GERANFreqGroupTableEntry
MAX-ACCESS                      not-accessible
STATUS                          current
DESCRIPTION
"
A row entry in geranFreqGroupTable.
"
INDEX { geranFreqGroupTblIndex }
::= { geranFreqGroupTable 1 }



geranFreqGroupTblIndex    OBJECT-TYPE
SYNTAX                    Unsigned32
MAX-ACCESS                not-accessible
STATUS                    current
DESCRIPTION
"
A unique index identifying a row in geranFreqGroupTable.
"
::= { geranFreqGroupTableEntry 1 }





geranFreqGroupTblQRxLevMin     OBJECT-TYPE
SYNTAX                         Unsigned32 (0..45)
MAX-ACCESS                     read-write
STATUS                         current
DESCRIPTION
"
REQUIRED minimum received RSSI level on this GERAN frequency carrier for
re-selection to this UTRA FDD carrier, specified in dBm. The value of
(QRxLevMin * 2 - 115) yields the actual value.
"
::= { geranFreqGroupTableEntry 2 }


geranFreqGroupTblCellReselectionPriority   OBJECT-TYPE
SYNTAX                                     Unsigned32 (0..7)
MAX-ACCESS                                 read-write
STATUS                                     current
DESCRIPTION
"
Absolute priority of this GERAN frequency group, as used by the
inter-frequency cell re-selection procedure.
"
::= { geranFreqGroupTableEntry 3 }


geranFreqGroupTblThreshXHigh    OBJECT-TYPE
SYNTAX                          Unsigned32 (0..31)
MAX-ACCESS                      read-write
STATUS                          current
DESCRIPTION
"
Threshold used when re-selecting towards a higher priority GERAN frequency
group than current serving E-UTRA frequency, specified in dB. The value of
(ThreshXHigh * 2) yields the actual value.
"
::= { geranFreqGroupTableEntry 4 }



geranFreqGroupTblThreshXLow     OBJECT-TYPE
SYNTAX                          Unsigned32 (0..31)
MAX-ACCESS                      read-write
STATUS                          current
DESCRIPTION
"
Threshold used when re-selecting towards a lower priority GERAN frequency
group than current serving E-UTRA frequency, specified in dB.
"
::= { geranFreqGroupTableEntry 5 }


--SPR 14225 start
eICICProvisionType OBJECT-TYPE
SYNTAX             ProvisionTypeeICIC
MAX-ACCESS         read-write
STATUS             current
DESCRIPTION
"
Parameter rameter is used for denoting the type according to which 
cell will behave
"

::= { cellConfigEICIC 1 }

eligibleUe         OBJECT-TYPE
SYNTAX             Unsigned32 (1..100)
MAX-ACCESS         read-write
STATUS             current
DESCRIPTION
"
Percentage of UEs to be selected for the eICIC out of total UEs 
experiencing interference
"

::= { cellConfigEICIC 3 }

dlSinrThreshLowMark OBJECT-TYPE
SYNTAX              Unsigned32 (0..255)
MAX-ACCESS          read-write
STATUS              current
DESCRIPTION
"
DL SINR value below which a UE is being identified as victim UE
"

::= { cellConfigEICIC 5 }

dlSinrThreshHighMark OBJECT-TYPE
SYNTAX               Unsigned32 (0..255)
MAX-ACCESS           read-write
STATUS               current
DESCRIPTION
"
DL SINR value above which a UE is being identified as non victim UE
"

::= { cellConfigEICIC 6 }

numAbsReport       OBJECT-TYPE
SYNTAX             Unsigned32 (0..1440)
MAX-ACCESS         read-write
STATUS             current
DESCRIPTION
"
Number of ABS status report received from victim eNB after which 
aggressor will take action to increase or decrease the ABS pattern.
"

::= { absInfo 1 }

absUsageLowThreshold OBJECT-TYPE
SYNTAX               Unsigned32 (1..100)
MAX-ACCESS           read-write
STATUS               current
DESCRIPTION
"
It indicates if the abs usage reported in resource status update message 
from victim is less than this value then ABS pattern needs to be decreased 
by one subframe
"

::= { absInfo 2 }

absUsageHighThreshold OBJECT-TYPE
SYNTAX                Unsigned32 (1..100)
MAX-ACCESS            read-write
STATUS                current
DESCRIPTION
"
It indicates if the abs usage reported in resource status update message 
from victim is greater than this value then ABS pattern needs to be increased 
by one subframe.
"

::= { absInfo 3 }

macEicicMeasReportPeriodicity OBJECT-TYPE
SYNTAX                        Unsigned32 (20..10000)
MAX-ACCESS                    read-write
STATUS                        current
DESCRIPTION
"
Periodicity at which MAC will send periodic eICIC measurement to RRM
"

::= { eicicTimerInfo 1 }

aggressorSelTimer  OBJECT-TYPE
SYNTAX             Unsigned32 (30..7200)
MAX-ACCESS         read-write
STATUS             current
DESCRIPTION
"
Periodic timer that activate eICIC algorithm on the victim UE present in the system
"

::= { eicicTimerInfo 2 }

loadInformationGuardTimer       OBJECT-TYPE
SYNTAX             Unsigned32 (1..15) 
MAX-ACCESS         read-write
STATUS             current
DESCRIPTION
"
Guard timer started to consolidate load information sent from different aggressors 
after sending invoke message to all aggressor nodes.
"

::= { eicicTimerInfo 3 }

loadInformationCollationTimer OBJECT-TYPE
SYNTAX                        Unsigned32 (1..60)
MAX-ACCESS                    read-write
STATUS                        current
DESCRIPTION
"
It indicates the timer interval for which RRM shall wait for collation of subsequent 
load information message in which ABS Information update is provided by aggressor 
without sending invoke by victim
"

::= { eicicTimerInfo 4 }

lowLoadAbsPattern            OBJECT-TYPE
SYNTAX                       DisplayString 
MAX-ACCESS                   read-write
STATUS                       current
DESCRIPTION
"
Used for providing ABS pattern to the node in case node is acting as aggressor node 
"

::= { absPattern 1 }

victimAbsPattern             OBJECT-TYPE
SYNTAX                       DisplayString
MAX-ACCESS                   read-write
STATUS                       current
DESCRIPTION
"
Used for providing ABS pattern to the victim node in case node is acting as victim node 
"

::= { absPattern 2 }

victimMeasSubset             OBJECT-TYPE
SYNTAX                       DisplayString 
MAX-ACCESS                   read-write
STATUS                       current
DESCRIPTION
"
This should be provided when no X2 connections exist with any of the neighbor of the cell.
This pattern is used for Measurement configuration
"

::= { absPattern 3 }



--SPR 14225 end

filterCoefficientRSRP OBJECT-TYPE
SYNTAX                FilteringCoefficientType
MAX-ACCESS            read-write
STATUS                current
DESCRIPTION
"
Filtering coefficient used for RSRP measurements.
"
::= { eutra 1 }



filterCoefficientRSRQ   OBJECT-TYPE
SYNTAX                  FilteringCoefficientType
MAX-ACCESS              read-write
STATUS                  current
DESCRIPTION
"
Filtering coefficient used for RSRQ measurements.
"
::= { eutra 2 }



a1ThresholdRSRP         OBJECT-TYPE
SYNTAX                  Unsigned32  (0..97)
MAX-ACCESS              read-write
STATUS                  current
DESCRIPTION
"
Threshold to be used in EUTRA measurement report triggering condition for
event A1. Valid only if TriggerQuantity is RSRP.
"
::= { eutra 3 }



a1ThresholdRSRQ         OBJECT-TYPE
SYNTAX                  Unsigned32  (0..34)
MAX-ACCESS              read-write
STATUS                  current
DESCRIPTION
"
Threshold to be used in EUTRA measurement report triggering condition for
event A1. Valid only if TriggerQuantity is RSRQ.
"
::= { eutra 4 }



a2ThresholdRSRP         OBJECT-TYPE
SYNTAX                  Unsigned32  (0..97)
MAX-ACCESS              read-write
STATUS                  current
DESCRIPTION
"
Threshold to be used in EUTRA measurement report triggering condition for
event A2. Valid only if TriggerQuantity is RSRP.
"
::= { eutra 5 }


a2ThresholdRSRQ         OBJECT-TYPE
SYNTAX                  Unsigned32  (0..34)
MAX-ACCESS              read-write
STATUS                  current
DESCRIPTION
"
Threshold to be used in EUTRA measurement report triggering condition for
event A2. Valid only if TriggerQuantity is RSRQ.
"
::= { eutra 6 }



a3Offset            OBJECT-TYPE
SYNTAX              Integer32 (-30..30)
MAX-ACCESS          read-write
STATUS              current
DESCRIPTION
"
Offset to be used in evaluation of EUTRA measurement report triggering
condition for event A3. 
"
::= { eutra 7 }


reportOnLeave       OBJECT-TYPE
SYNTAX              BoolType 
MAX-ACCESS          read-write
STATUS              current
DESCRIPTION
"
Indicates whether or not the UE shall initiate the measurement reporting
procedure when the leaving condition is met for event A3 for a cell in
cellsTriggeredList.
"
::= { eutra 8 }


a4ThresholdRSRP     OBJECT-TYPE
SYNTAX              Unsigned32  (0..97)
MAX-ACCESS          read-write
STATUS              current
DESCRIPTION
"
Threshold to be used in EUTRA measurement report triggering condition for
event A4. Valid only if TriggerQuantity is RSRP.
"
::= { eutra 9 }


a4ThresholdRSRQ     OBJECT-TYPE
SYNTAX              Unsigned32  (0..34)
MAX-ACCESS          read-write
STATUS              current
DESCRIPTION
"
Threshold to be used in EUTRA measurement report triggering condition for
event A4. Valid only if TriggerQuantity is RSRQ.
"
::= { eutra 10 }



a5Threshold1RSRP        OBJECT-TYPE
SYNTAX                  Unsigned32  (0..97)
MAX-ACCESS              read-write
STATUS                  current
DESCRIPTION
"
Threshold1 to be used in EUTRA measurement report triggering condition for
event A5. Valid only if TriggerQuantity is RSRP. 
"
::= { eutra 11 }


a5Threshold1RSRQ        OBJECT-TYPE
SYNTAX                  Unsigned32  (0..34)
MAX-ACCESS              read-write
STATUS                  current
DESCRIPTION
"
Threshold1 to be used in EUTRA measurement report triggering condition for
event A5. Valid only if TriggerQuantity is RSRQ
"
::= { eutra 12 }


a5Threshold2RSRP        OBJECT-TYPE
SYNTAX                  Unsigned32  (0..97)
MAX-ACCESS              read-write
STATUS                  current
DESCRIPTION
"
Threshold2 to be used in EUTRA measurement report triggering condition for
event A5. Valid only if TriggerQuantity is RSRP.
"
::= { eutra 13 }


a5Threshold2RSRQ        OBJECT-TYPE
SYNTAX                  Unsigned32  (0..34)
MAX-ACCESS              read-write
STATUS                  current
DESCRIPTION
"
Threshold2 to be used in EUTRA measurement report triggering condition for
event A5. Valid only if TriggerQuantity is RSRQ. 
"
::= { eutra 14 }


eutraHysteresis         OBJECT-TYPE
SYNTAX                  Unsigned32 (0..30)
MAX-ACCESS              read-write
STATUS                  current
DESCRIPTION
"
Hysteresis value applied to entry and leave condition of a report triggering
event., with a numeric range between 0 and 30 inclusive
"
::= { eutra 15 }


eutraTimeToTrigger      OBJECT-TYPE
SYNTAX                  TimeToTriggerType
MAX-ACCESS              read-write
STATUS                  current
DESCRIPTION
"
Time period during which measurement report triggering condition needs to be
met in order to trigger a measurement report, specified in milliseconds.
"
::= { eutra 16 }


triggerQuantity         OBJECT-TYPE
SYNTAX                  DisplayString
MAX-ACCESS              read-write
STATUS                  current
DESCRIPTION
"
Quantities used to evaluate a measurement report triggering condition.
Enumeration of:

  * RSRP
  * RSRQ 
"
::= { eutra 17 }


reportQuantity      OBJECT-TYPE
SYNTAX              DisplayString
MAX-ACCESS          read-write
STATUS              current
DESCRIPTION
"
Measrument quantities to be included in the measurement report. The value
Both specifies that both the RSRP and RSRQ quantities are to be included in
the measurement report. Enumeration of:

  * SameAsTriggerQuantity
  * Both 
"
::= { eutra 18 }


eutraReportInterval OBJECT-TYPE
SYNTAX              ReportIntervalType
MAX-ACCESS          read-write
STATUS              current
DESCRIPTION
"
Interval between successive measurement reports, specified in milliseconds.
"
::= { eutra 19 }


eutraReportAmount OBJECT-TYPE
SYNTAX            ReportAmountType
MAX-ACCESS        read-write
STATUS            current
DESCRIPTION
"
Number of times a measurement report is sent.
"
::= { eutra 20 }



qOffsettUTRA        OBJECT-TYPE
SYNTAX              Integer32 (-15..15)
MAX-ACCESS          read-write
STATUS current
DESCRIPTION
"
Indicates UTRA-specific offset to be applied when evaluating triggering
conditions for measurement reporting in connected mode.
"
::= { connModeIRAT 1 }


filterCoefficientUTRA OBJECT-TYPE
SYNTAX                FilteringCoefficientType
MAX-ACCESS            read-write
STATUS                current
DESCRIPTION
"
Filtering coefficient used for UTRA measurements.
"
::= { connModeIRAT 2 }



measQuantityUTRAFDD     OBJECT-TYPE
SYNTAX                  DisplayString
MAX-ACCESS              read-write
STATUS                  current
DESCRIPTION
"
Measurement quantity used for UTRA measurements.
"
::= { connModeIRAT 3 }



b1ThresholdUTRARSCP        OBJECT-TYPE
SYNTAX                     Integer32 (-5..91)
MAX-ACCESS                 read-write
STATUS                     current
DESCRIPTION
"
RSCP threshold to be used in UTRA measurement report triggering condition for
event B1.
"
::= { connModeIRAT 4 }


b1ThresholdUTRAEcN0     OBJECT-TYPE
SYNTAX                  Unsigned32  (0..49)
MAX-ACCESS              read-write
STATUS                  current
DESCRIPTION
"
EcNo threshold to be used in UTRA measurement report triggering condition for
event B1.
"
::= { connModeIRAT 5 }


qoffsetGERAN        OBJECT-TYPE
SYNTAX              Integer32 (-15..15)
MAX-ACCESS          read-write
STATUS              current
DESCRIPTION
"
GERAN-specific offset to be applied when evaluating triggering conditions for
measurement reporting in connected mode.
"
::= { connModeIRAT 6 }



filterCoefficientGERAN      OBJECT-TYPE
SYNTAX                      FilteringCoefficientType
MAX-ACCESS                  read-write
STATUS                      current
DESCRIPTION
"
Filtering coefficient used for GERAN measurements.
"
::= { connModeIRAT 7 }



b1ThresholdGERAN        OBJECT-TYPE
SYNTAX                  Unsigned32 (1..63)
MAX-ACCESS              read-write
STATUS                  current
DESCRIPTION
"
Threshold to be used in GERAN measurement report triggering condition for
event B1.
"
::= { connModeIRAT 8 }



qoffsetCDMA2000         OBJECT-TYPE
SYNTAX                  Integer32 (-15..15)
MAX-ACCESS              read-write
STATUS                  current
DESCRIPTION
"
CDMA2000-specific offset to be applied when evaluating triggering conditions
for measurement reporting in connected mode.
"
::= { connModeIRAT 9 }



measQuantityCDMA2000    OBJECT-TYPE
SYNTAX                  DisplayString 
MAX-ACCESS              read-write
STATUS                  current
DESCRIPTION
"
Measurement quantity used for CDMA2000 measurements. Enumeration of:

  * PilotStrength
  * PilotPnPhaseAndPilotStrength 
"
::= { connModeIRAT 10 }



b1ThresholdCDMA2000     OBJECT-TYPE
SYNTAX                  Unsigned32 (0..63)
MAX-ACCESS              read-write
STATUS                  current
DESCRIPTION
"
Threshold to be used in CDMA2000 measurement report triggering condition for
event B1
"
::= { connModeIRAT 11 }



b2Threshold2UTRARSCP    OBJECT-TYPE
SYNTAX                  Integer32  (-5..91)
MAX-ACCESS              read-write
STATUS                  current
DESCRIPTION
"
RSCP threshold to be used in UTRA measurement report triggering condition for
event B2.
"
::= { connModeIRAT 12 }



b2Threshold2UTRAEcN0    OBJECT-TYPE
SYNTAX                  Unsigned32  (0..49)
MAX-ACCESS              read-write
STATUS                  current
DESCRIPTION
"
EcNo threshold to be used in UTRA measurement report triggering condition for
event B2.
"
::= { connModeIRAT 13 }



b2Threshold2GERAN       OBJECT-TYPE
SYNTAX                  Unsigned32  (0..63)
MAX-ACCESS              read-write
STATUS                  current
DESCRIPTION
"
Threshold to be used in GERAN measurement report triggering condition for
event B2.
"
::= { connModeIRAT 14 }



b2Threshold2CDMA2000    OBJECT-TYPE
SYNTAX                  Unsigned32  (0..63)
MAX-ACCESS              read-write
STATUS                  current
DESCRIPTION
"
Threshold to be used in CDMA2000 measurement report triggering condition for
event B2.
"
::= { connModeIRAT 15 }



iratHysteresis      OBJECT-TYPE
SYNTAX              Unsigned32 (0..30)
MAX-ACCESS          read-write
STATUS              current
DESCRIPTION
"
Hysteresis value applied to entry and leave condition of an IRAT report
triggering event.
"
::= { connModeIRAT 16 }



iratTimeToTrigger   OBJECT-TYPE
SYNTAX              TimeToTriggerType
MAX-ACCESS          read-write
STATUS              current
DESCRIPTION
"
Time period during which IRAT measurement report triggering condition needs
to be met in order to trigger IRAT measurement report, specified in
milliseconds.
"
::= { connModeIRAT 17 }




maxReportCells      OBJECT-TYPE
SYNTAX              Unsigned32  (1..8)
MAX-ACCESS          read-only
STATUS              current
DESCRIPTION
"
Maximum number of IRAT cells that can be included in a measurement report.
"
::= { connModeIRAT 18 }



iratReportInterval      OBJECT-TYPE
SYNTAX                  ReportIntervalType
MAX-ACCESS              read-write
STATUS                  current
DESCRIPTION
"
Interval between successive IRAT measurement reports, specified in
milliseconds.
"
::= { connModeIRAT 19 }



iratReportAmount OBJECT-TYPE
SYNTAX           ReportAmountType
MAX-ACCESS       read-write
STATUS           current
DESCRIPTION
"
Number of times an IRAT measurement report is sent.
"
::= { connModeIRAT 20 }




earfcnDL        OBJECT-TYPE
SYNTAX          DisplayString (SIZE(1..128))
MAX-ACCESS      read-write
STATUS          current
DESCRIPTION
"
Comma-separated list (maximum length 128) (at least 1 items) of unsigned
integers (value 0 to 65535). Each item is an E-UTRA Absolute Radio Frequency
Channel Number in the downlink direction. In case there is more than one item
in the list, the first item contains the most preferred value.
"
::= { rf 1 }



earfcnUL        OBJECT-TYPE
SYNTAX          DisplayString (SIZE(1..128))
MAX-ACCESS      read-write
STATUS          current
DESCRIPTION
"
Comma-separated list (maximum length 128) (at least 1 items) of unsigned
integers (value 0 to 65535). Each item is an E-UTRA Absolute Radio Frequency
Channel Number in the uplink direction. In case there is more than one item
in the list, the first item contains the most preferred value
"
::= { rf 2 }



freqBandIndicator       OBJECT-TYPE
SYNTAX                  Unsigned32 (1..43)
MAX-ACCESS              read-write
STATUS                  current
DESCRIPTION
"
Frequency band indicator.
"
::= { rf 3 }



dlBandwidth             OBJECT-TYPE
SYNTAX                  DisplayString
MAX-ACCESS              read-write
STATUS                  current
DESCRIPTION
"
Downlink transmission bandwidth, specified in number of Resource Blocks.
Enumeration of:

  * n6
  * n15
  * n25
  * n50
  * n75
  * n100 
"
::= { rf 4 }



ulBandwidth             OBJECT-TYPE
SYNTAX                  DisplayString
MAX-ACCESS              read-write
STATUS                  current
DESCRIPTION
"
Uplink transmission bandwidth, specified in number of Resource Blocks.
Enumeration of:

  * n6
  * n15
  * n25
  * n50
  * n75
  * n100 
"
::= { rf 5 }



referenceSignalPower    OBJECT-TYPE
SYNTAX                  Integer32 (-60..50)
MAX-ACCESS              read-write
STATUS                  current
DESCRIPTION
"
The downlink reference-signal transmit power, specified in dBm. Defined as
the linear average over the power contributions (in W) of all resource
elements that carry cell-specific reference signals within the operating
system bandwidth.
"
::= { rf 6 }



rfPhyCellID             OBJECT-TYPE
SYNTAX                  DisplayString (SIZE(1..64))
MAX-ACCESS              read-write
STATUS                  current
DESCRIPTION
"
Comma-separated list (maximum length 64) (at least 1 items) of unsigned
integers (value 0 to 503). Each item is a physical cell ID with a numeric
range between 0 and 503 inclusive. Represents the list of physical cell
identities LTE device to choose from.
"
::= { rf 7 }



pschPowerOffset         OBJECT-TYPE
SYNTAX                  Integer32 (-60..40)
MAX-ACCESS              read-write
STATUS                  current
DESCRIPTION
"
The power offset, specified in 0.1 dB of the Primary Synchronization Channel
with respect to the ReferenceSignalPower. The value of PSCHPowerOffset
divided by 10 yields the actual value. For example, value -30 represents -3
dB; value 120 represent 12 dB etc.
"
::= { rf 8 }



sschPowerOffset         OBJECT-TYPE
SYNTAX                  Integer32 (-60..40)
MAX-ACCESS              read-write
STATUS                  current
DESCRIPTION
"
The power offset, specified in 0.1 dB of the Secondary Synchronization
Channel with respect to the ReferenceSignalPower. The value of
SSCHPowerOffset divided by 10 yields the actual value. For example, value -30
represents -3 dB; value 120 represent 12 dB etc.
"
::= { rf 9 }



pbchPowerOffset         OBJECT-TYPE
SYNTAX                  Integer32 (-60..40)
MAX-ACCESS              read-write
STATUS                  current
DESCRIPTION
"
The power offset, specified in 0.1 dB of the Physical Broadcast Channel with
respect to the ReferenceSignalPower. The value of PBCHPowerOffset divided by
10 yields the actual value. For example, value -30 represents -3 dB; value
120 represent 12 dB etc.
"
::= { rf 10 }



antennaPortsCount       OBJECT-TYPE
SYNTAX                  AntennaPortsCountType
MAX-ACCESS              read-only
STATUS                  current
DESCRIPTION
"
Defines the number of cell specific antenna ports according to
[Section 6.2.1/3GPP-TS.36.211]. A UE in IDLE mode acquires the information
about the number of transmit antenna ports according to
[Section 5.3.1.1/3GPP-TS.36.212]. 
"
::= { antennaInfo 1 }



pb              OBJECT-TYPE
SYNTAX          Unsigned32 (0..3)
MAX-ACCESS      read-write
STATUS          current
DESCRIPTION
"
Eb/Ea value. The value of this parameter is the same for all UEs in the cell.
"
::= { pdsch 1 }



pa              OBJECT-TYPE
SYNTAX          PaType
MAX-ACCESS      read-write
STATUS          current
DESCRIPTION
"
Ea/Ers value specified in 0.01 dB.

Ea = EPRE (energy per resource element) of PDSCH REs type A, i.e. REs in OFDM
symbols that do not include reference symbols.

Ers = EPRE (energy per resource element) of of reference symbols REs. 
"
::= { pdsch 2 }



srsEnabled      OBJECT-TYPE
SYNTAX          BoolType
MAX-ACCESS      read-write
STATUS          current
DESCRIPTION
"
Indicates whether UL SRS (Sounding RS) is enabled or not.

If true, UL Sounding RS is enabled. If false, UL Sounding RS is disabled.
"
::= { srs 1 }



srsBandwidthConfig      OBJECT-TYPE
SYNTAX                  DisplayString
MAX-ACCESS              read-write
STATUS                  current
DESCRIPTION
"
Denotes an index into tables with cell specific SRS Bandwidth Configuration.
Enumeration of Enumeration of:

  * bw0
  * bw1
  * bw2
  * bw3
  * bw4
  * bw5
  * bw6
  * bw7 
"
::= { srs 2 }



srsMaxUpPTS      OBJECT-TYPE
SYNTAX           BoolType
MAX-ACCESS       read-write
STATUS           current
DESCRIPTION
"
Defines whether reconfiguration of SRS applies to UpPTS or not.

If true, SRS applies to UpPTS. If false, SRS does not apply to UpPTS.

"
::= { srs 3 }



ackNackSRSSimultaneousTransmission  OBJECT-TYPE
SYNTAX                              BoolType
MAX-ACCESS                          read-write
STATUS                              current
DESCRIPTION
"
Defines whether a UE can simultaneously transmit SRS and HARQ ACK/NACK or
not.

If true, simultaneous transmission is allowed. If false, simultaneous
transmission is not allowed.
"
::= { srs 4 }



rootSequenceIndex  OBJECT-TYPE
SYNTAX             Unsigned32 (1..837)
MAX-ACCESS         read-write
STATUS             current
DESCRIPTION
"
Logical root sequence index used to determine 64 physical RACH preamble
sequences available in the cell.
"
::= { prach 1 }



configurationIndex  OBJECT-TYPE
SYNTAX             Unsigned32(0..63)
MAX-ACCESS         read-write
STATUS             current
DESCRIPTION
"
Provides index into the table defining PRACH resources within the frame.
"
::= { prach 2 }



highSpeedFlag      OBJECT-TYPE
SYNTAX             BoolType
MAX-ACCESS         read-write
STATUS             current
DESCRIPTION
"
Indicates whether restricted set or unrestricted set of preambles is used.

If true, indicates restricted set. If false, indicates unrestricted set.

"
::= { prach 3 }


zeroCorrelationZoneConfig   OBJECT-TYPE
SYNTAX                      Unsigned32(0..15)
MAX-ACCESS                  read-write
STATUS                      current
DESCRIPTION
"
This parameter is used for preamble sequence generation.
"
::= { prach 4 }



freqOffset   OBJECT-TYPE
SYNTAX       Unsigned32 (0..94)
MAX-ACCESS   read-write
STATUS       current
DESCRIPTION
"
The first available physical resource block number for PRACH.
"
::= { prach 5 }



deltaPUCCHShift   OBJECT-TYPE
SYNTAX            DisplayString
MAX-ACCESS        read-write
STATUS            current
DESCRIPTION
"
Defines the cyclic shift used for PUCCH formats 1/1a/1b in a resource block
used for a mix of formats 1/1a/1b and 2/2a/2b.
It is an integer multiple of deltaPUCCHShift within the range of
{0, 1, ., 7}. Enumeration of:

  * ds1
  * ds2
  * ds3 
"
::= { pucch 1 }



nrbcqi            OBJECT-TYPE
SYNTAX            Unsigned32 (0..98)
MAX-ACCESS        read-write
STATUS            current
DESCRIPTION
"
Defines the bandwidth in terms of resource blocks that are available for use
by PUCCH formats 2/2a/2b transmission in each slot.
"
::= { pucch 2 }



ncsan             OBJECT-TYPE
SYNTAX            Unsigned32 (0..7)
MAX-ACCESS        read-only
STATUS            current
DESCRIPTION
"
Defines the number of cyclic shift used for PUCCH formats 1/1a/1b in a
resource block used for a mix of formats 1/1a/1b and 2/2a/2b.

The value is an integer multiple of deltaPUCCHShift within the range of
{0, 1, ., 7}.
"
::= { pucch 3 }



n1PUCCHAN         OBJECT-TYPE
SYNTAX            Unsigned32 (0..2047)
MAX-ACCESS        read-write
STATUS            current
DESCRIPTION
"
Parameter used to determine resources used for transmission of PUCCH format
1/1a/1b and 2/2a/2b.
"
::= { pucch 4 }


-- SPR 22311 Changes - Obselete Parameter Deleted


nsb             OBJECT-TYPE
SYNTAX          Unsigned32 (1..4)
MAX-ACCESS      read-write
STATUS          current
DESCRIPTION
"
Defines the number of sub-bands.
"
::= { pusch 1 }



hoppingMode     OBJECT-TYPE
SYNTAX          DisplayString
MAX-ACCESS      read-write
STATUS          current
DESCRIPTION
"
Indicates if hopping is 'inter-subframe' or 'intra and inter-subframe'.
Enumeration of:

  * InterSubFrame
  * IntraAndInterSubFrame 
"
::= { pusch 2 }



hoppingOffset   OBJECT-TYPE
SYNTAX          Unsigned32 (0..98)
MAX-ACCESS      read-write
STATUS          current
DESCRIPTION
"
This parameter is used to compute the set of physical resource blocks to be
used for transmission on PUSCH if uplink frequency hopping mode is enabled.
"
::= { pusch 3 }



enable64QAM     OBJECT-TYPE
SYNTAX          BoolType
MAX-ACCESS      read-only
STATUS          current
DESCRIPTION
"
Indicates whether 64QAM is allowed or not. If true, 64QAM is allowed. If
false, 64QAM is not allowed.
"
::= { pusch 4 }



groupHoppingEnabled    OBJECT-TYPE
SYNTAX                 BoolType
MAX-ACCESS             read-write
STATUS                 current
DESCRIPTION
"
Indicates whether group hopping is enabled or not. If true, group hopping is
enabled. If false, group hopping is not enabled.
"
::= { ulrs 1 }



groupAssignmentPUSCH    OBJECT-TYPE
SYNTAX                  Unsigned32 (0..29)
MAX-ACCESS              read-only
STATUS                  current
DESCRIPTION
"
Corresponds to parameter groupAssignmentPUSCH specified in
[Section 6.3.2/3GPP-TS.36.331].
"
::= { ulrs 2 }



sequenceHoppingEnabled    OBJECT-TYPE
SYNTAX                    BoolType
MAX-ACCESS                read-write
STATUS                    current
DESCRIPTION
"
Indicates whether sequence hopping is enabled or not. If true, sequence
hopping is enabled. If false, sequence hopping is not enabled.
"
::= { ulrs 3 }



cyclicShift               OBJECT-TYPE
SYNTAX                    Unsigned32 (0..7)
MAX-ACCESS                read-only
STATUS                    current
DESCRIPTION
"
Corresponds to parameter cyclcShift specified in
[Section 6.3.2/3GPP-TS.36.331].
"
::= { ulrs 4 }




p0NominalPUSCH            OBJECT-TYPE
SYNTAX                    Integer32 (-126..24)
MAX-ACCESS                read-write
STATUS                    current
DESCRIPTION
"
Denotes the parameter used to compute the UL UE transmit power for
transmission on PUSCH for semi-persistent grants.
"
::= { ulPowerControl 1 }




alpha                     OBJECT-TYPE
SYNTAX                    AlphaType
MAX-ACCESS                read-write
STATUS                    current
DESCRIPTION
"
Value used to compute the UL UE transmit power for transmission on PUSCH.
Actual values of range are from 0.00 to 1.00. The value of Alpha divided by
100 yields the actual value.
"
::= { ulPowerControl 2 }



p0NominalPUCCH            OBJECT-TYPE
SYNTAX                    Integer32 (-127..-96)
MAX-ACCESS                read-write
STATUS                    current
DESCRIPTION
"
Value to compute the UL UE transmit power for transmission on PUCCH.
"
::= { ulPowerControl 3 }





deltaFPUCCHFormat1        OBJECT-TYPE
SYNTAX                    DeltaFPUCCHFormat1Type
MAX-ACCESS                read-only
STATUS                    current
DESCRIPTION
"
Defines deltaF-PUCCH-Format1 to derive the UE transmit power.
"
::= { ulPowerControl 4 }




deltaFPUCCHFormat1b       OBJECT-TYPE
SYNTAX                    DeltaFPUCCHFormat1bType
MAX-ACCESS                read-only
STATUS                    current
DESCRIPTION
"
Defines deltaF-PUCCH-Format1b to derive the UE transmit power.
"
::= { ulPowerControl 5 }




deltaFPUCCHFormat2        OBJECT-TYPE
SYNTAX                    DeltaFPUCCHFormat2Type
MAX-ACCESS                read-only
STATUS                    current
DESCRIPTION
"
Defines deltaF-PUCCH-Format2 to derive the UE transmit power.
"
::= { ulPowerControl 6 }



deltaFPUCCHFormat2a       OBJECT-TYPE
SYNTAX                    DeltaFPUCCHFormat2aType
MAX-ACCESS                read-only
STATUS                    current
DESCRIPTION
"
Defines deltaF-PUCCH-Format2a to derive the UE transmit power.
"
::= { ulPowerControl 7 }



deltaFPUCCHFormat2b       OBJECT-TYPE
SYNTAX                    DeltaFPUCCHFormat2bType
MAX-ACCESS                read-only
STATUS                    current
DESCRIPTION
"
Defines deltaF-PUCCH-Format2b to derive the UE transmit power.
"
::= { ulPowerControl 8 }



deltaPreambleMsg3         OBJECT-TYPE
SYNTAX                    Integer32  (-1..6)
MAX-ACCESS                read-only
STATUS                    current
DESCRIPTION
"
Defines the parameter in dB used to compute the UL UE transmit power for
transmission of random access response grant.
"
::= { ulPowerControl 9 }



numPRSResourceBlocks   OBJECT-TYPE
SYNTAX                 Unsigned32  (0..255)
MAX-ACCESS             read-write
STATUS                 current
DESCRIPTION
"
Defines the number of RBs (Resource Blocks) used for PRS.
Supported Values: (0-5)
Enumeration of:
 * N6
 * N15
 * N25
 * N50
 * N75
 * N100
"
::= { prs 1 }



prsConfigurationIndex   OBJECT-TYPE
SYNTAX                  Unsigned32 (0..4095)
MAX-ACCESS              read-write
STATUS                  current
DESCRIPTION
"
Corresponds to the PRS configuration index defined as parameter IPRS in
[Section 6.10.4.3 and Table 6.10.4.3.-1/3GPP-TS.36.211].
"
::= { prs 2 }



numConsecutivePRSSubframes   OBJECT-TYPE
SYNTAX                      INTEGER { n1(1), n2(2), n4(4), n6(6) }
MAX-ACCESS                  read-write
STATUS                      current
DESCRIPTION
"
Defines the number of consecutive positioning sub-frames.
"
::= { prs 3 }



subFrameAssignment   OBJECT-TYPE
SYNTAX               Unsigned32 (0..6)
MAX-ACCESS           read-write
STATUS               current
DESCRIPTION
"
Defines the DL/UL sub-frame configuration.
"
::= { tddFrame 1 }



specialSubframePatterns   OBJECT-TYPE
SYNTAX                    Unsigned32 (0..8)
MAX-ACCESS                read-write
STATUS                    current
DESCRIPTION
"
Defines the configuration of the special sub-frame that contains the guard
period between the downlink and uplink transmissions.
"
::= { tddFrame 2 }



neighCellConfig    OBJECT-TYPE
SYNTAX             Unsigned32 (0..3)
MAX-ACCESS         read-write
STATUS             current
DESCRIPTION
"
Defines the information related to MBSFN and TDD UL/DL configuration of
neighbour cells.Corresponds to NeighCellConfig IE specified in
[Section 6.3.6/3GPP-TS.36.331].
Value 0: Not all neighbour cells have the same MBSFN sub-frame allocation as
         serving cell.
Value 1: No MBSFN sub-frames are present in all neighbour cells.
Value 2: The MBSFN sub-frame allocations of all neighbour cells are identical to
         or subsets of that in the serving cell.
Value 3: Different UL/DL allocation in neighbouring cells for TDD compared to
         the serving cell.
"
::= { mbsfn 1 }



maxSFConfigListEntries   OBJECT-TYPE
SYNTAX                   Unsigned32
MAX-ACCESS               read-only
STATUS                   current
DESCRIPTION
"
The max number of entries in the CellConfig.LTE.RAN.PHY.MBSFN.SFConfigList.{i}
table.
"
::= { mbsfn 2 }



sfConfigListNumberOfEntries    OBJECT-TYPE
SYNTAX                         Unsigned32
MAX-ACCESS                     read-only
STATUS                         current
DESCRIPTION
"
The number of entries in the SFConfigList table.
"
::={ mbsfn 3 }



sfConfigListTable    OBJECT-TYPE
SYNTAX SEQUENCE OF   SFConfigListTableEntry
MAX-ACCESS           not-accessible
STATUS               current
DESCRIPTION          
"
This object contains parameters relating to the sub-frame that are reserved for
MBSFN in downlink direction. For FDD mode, only one entry can exist in this
table. For TDD mode, at most one entry can exist with a given value of stratumID
(see [Section 6.1.1.8/3GPP-TS.32.592]).
At most one enabled entry in this table can exist with all the same values for
RadioFrameAllocationPeriod, RadioframeAllocationOffset and RadioFrameAllocationSize.
"
::= { mbsfn 4 }



SFConfigListTableEntry ::= SEQUENCE {
        sfConfigListTblIndex                               Unsigned32,
        sfConfigListTblSyncStratumID                       Unsigned32,
        sfConfigListTblRadioFrameAllocationPeriod          Unsigned32,
        sfConfigListTblRadioframeAllocationOffset          Unsigned32,
        sfConfigListTblRadioFrameAllocationSize            Unsigned32,
        sfConfigListTblSubFrameAllocations                 DisplayString
}



sfConfigListTableEntry    OBJECT-TYPE
SYNTAX                    SFConfigListTableEntry
MAX-ACCESS                not-accessible
STATUS                    current
DESCRIPTION
"
A row entry in sfConfigListTable table.
"
INDEX { sfConfigListTblIndex }
::= { sfConfigListTable 1 }



sfConfigListTblIndex    OBJECT-TYPE
SYNTAX                  Unsigned32
MAX-ACCESS              not-accessible
STATUS                  current
DESCRIPTION
"
A unique index to identify a row in sfConfigListTable table.
"
::= { sfConfigListTableEntry 1 }



sfConfigListTblSyncStratumID    OBJECT-TYPE
SYNTAX                          Unsigned32 (1..8)
MAX-ACCESS                      read-write
STATUS                          current
DESCRIPTION
"
This parameter is applicable to TDD mode only. Defines the synchronization
stratum level to which the MBSFN configuration applies.
"
::= { sfConfigListTableEntry 2 }


sfConfigListTblRadioFrameAllocationPeriod    OBJECT-TYPE
SYNTAX                                       Unsigned32 ( 1 | 2 | 4 | 8 | 16 | 32 )
MAX-ACCESS                                   read-write
STATUS                                       current
DESCRIPTION
"
Defines the period where MBSFN sub-frames occur in the radio frames.
Radio frames contain MBSFN sub-frame when the following condition
is met:
((SFN mod RadioFrameAllocationPeriod) = RadioframeAllocationOffset).
The value of 1 and 2 are only meaningful when the value of
RadioFrameAllocationSize parameter is 1. Corresponds to
radioFrameAllocationPeriod IE specified in
[Section 6.3.1/3GPP-TS.36.331].
"
::= { sfConfigListTableEntry 3 }



sfConfigListTblRadioframeAllocationOffset    OBJECT-TYPE
SYNTAX                                       Unsigned32 (0..7)
MAX-ACCESS                                   read-write
STATUS                                       current
DESCRIPTION
"
Defines the offset where MBSFN sub-frames occur in the radio frames.
Radio frames contain MBSFN sub-frame when the following condition is met:
((SFN mod RadioFrameAllocationPeriod) = RadioframeAllocationOffset).
Corresponds to radioFrameAllocationOffset IE specified in [Section 6.3.1/3GPP-TS.36.331].
"
::= { sfConfigListTableEntry 4 }



sfConfigListTblRadioFrameAllocationSize    OBJECT-TYPE
SYNTAX                                     Unsigned32 ( 1|4 )
MAX-ACCESS                                 read-write
STATUS                                     current
DESCRIPTION
"
Defines the number of connsecutive frames that the MBSFN allocation pertains to
defined by the combination of RadioFrameAllocationPeriod and
RadioframeAllocationOffset parameters.
"
::= { sfConfigListTableEntry 5 }



sfConfigListTblSubFrameAllocations    OBJECT-TYPE
SYNTAX                                DisplayString (SIZE(11..64))
MAX-ACCESS                            read-write
STATUS                                current
DESCRIPTION
"
Comma-separated list (maximum length 64) of unsigned integers (value 0, or 1).
The value of 1 indicates the position of sub-frames that is allocated to
MBSFN within the radio frame. 1st item defines the MBSFN allocation for
sub-frame #1, 2nd item for #2, 3rd item for #3, 4th item for #6,
5th item for #7, 6th item for #8. If the value of RadioFrameAllocationSize is 4,
then this pattern repeats in the sequence of the four radio frames.
If the value of RadioFrameAllocationSize is 1, then the size of this parameter
is 6; if the size RadioFrameAllocationSize is 4, then the size of this parameter
is 24.
Corresponds to subframeAllocation IE specified in [Section 6.3.1/3GPP-TS.36.331].
"
::= { sfConfigListTableEntry 6 }



neighborListMaxLTECellEntries   OBJECT-TYPE
SYNTAX                          Unsigned32
MAX-ACCESS                      read-only
STATUS                          current
DESCRIPTION
"
The maximum number of entries in the neighborListLTECellTable.
"
::= { neighborList 1 }



neighborListLTECellNumberOfEntries   OBJECT-TYPE
SYNTAX                               Unsigned32
MAX-ACCESS                           read-only
STATUS                               current
DESCRIPTION
"
The number of entries in the neighborListLTECellTable.
"
::= { neighborList 2 }


neighborListLTECellTable             OBJECT-TYPE
SYNTAX SEQUENCE OF                   NeighborListLTECellTableEntry
MAX-ACCESS                           not-accessible
STATUS                               current
DESCRIPTION
"
Table containing the E-UTRA (i.e. intra-RAT) cell list provided by the ACS.
The table contents MAY be added/deleted/modified during operation, in which
case these changes shall be reflected in the broadcast information as soon as
possible.
"
::= { neighborList 3 }



NeighborListLTECellTableEntry ::= SEQUENCE {
        neighborListLTECellTblIndex                            Unsigned32,
        neighborListLTECellTblPLMNID                           DisplayString,
        neighborListLTECellTblCID                              Unsigned32,
        neighborListLTECellTblEUTRACarrierARFCN                Unsigned32,
        neighborListLTECellTblPhyCellID                        Unsigned32,
        neighborListLTECellTblQOffset                          QOffsetType,
        neighborListLTECellTblCIO                              INTEGER,
        neighborListLTECellTblBlacklisted                      BoolType
}



neighborListLTECellTableEntry     OBJECT-TYPE
SYNTAX                            NeighborListLTECellTableEntry
MAX-ACCESS                        not-accessible
STATUS                            current
DESCRIPTION
"
A row entry in neighborListLTECellTable.
Combination of neighborListLTECellTblPLMNID & neighborListLTECellTblCID forms the key element of each row
"
INDEX { neighborListLTECellTblIndex }
::= { neighborListLTECellTable 1 }



neighborListLTECellTblIndex   OBJECT-TYPE
SYNTAX                        Unsigned32
MAX-ACCESS                    not-accessible
STATUS                        current
DESCRIPTION
"
A unique index identifying a row in neighborListLTECellTable.
"
::= { neighborListLTECellTableEntry 1 }



neighborListLTECellTblPLMNID   OBJECT-TYPE
SYNTAX                         DisplayString
MAX-ACCESS                     read-write
STATUS                         current
DESCRIPTION
"
PLMN ID consists of Mobile Country Code (MCC) and Mobile Network Code (MNC)
[3GPP-TS.23.003], [3GPP-TS.24.008].

Mobile Country Code consists of three digits and uniquely identifies the
country of domicile of the subscriber.

Mobile Network Code consists of two or three digits and identifies the Home
PLMN within a country.

Note : neighborListLTECellTblPLMNID is part of key element of each row 
hence SET for neighborListLTECellTblPLMNID parameter is not supoorted.
"
::= { neighborListLTECellTableEntry 2 }



neighborListLTECellTblCID      OBJECT-TYPE
SYNTAX                         Unsigned32 (1..268435455)
MAX-ACCESS                     read-write
STATUS                         current
DESCRIPTION
"
Cell Identity. [Section 6.3.4/3GPP-TS.36.331]. Combination of PLMNID and CID
constitutes the Cell Global ID (CGI).

Note : neighborListLTECellTblCID is part of key element of each row
hence SET for neighborListLTECellTblCID parameter is not supoorted.
"
::= { neighborListLTECellTableEntry 3 }



neighborListLTECellTblEUTRACarrierARFCN      OBJECT-TYPE
SYNTAX                                       Unsigned32 (0..65535)
MAX-ACCESS                                   read-write
STATUS                                       current
DESCRIPTION
"
Indicates the ARFCN of this carrier frequency. Corresponds to parameter
dl-CarrierFreq in SIB5 in [Section 6.3.1/3GPP-TS.36.331], and and parameter
NDL in [Section 5.7.3/3GPP-TS.36.101]. If the value of EUTRACarrierARFCN is
the same with the one currently being used by the, then it implies that this
neighbor cell is an intra-frequency cell; otherwise, it is an inter-frequency
cell.
"
::= { neighborListLTECellTableEntry 4 }



neighborListLTECellTblPhyCellID    OBJECT-TYPE
SYNTAX                             Unsigned32 (0..503)
MAX-ACCESS                         read-write
STATUS                             current
DESCRIPTION
"
Physical cell ID, as specified in [Section 6.11/3GPP-TS.36.211].
"
::= { neighborListLTECellTableEntry 5 }


neighborListLTECellTblQOffset    OBJECT-TYPE
SYNTAX                           QOffsetType
MAX-ACCESS                       read-write
STATUS                           current
DESCRIPTION
"
Indicate a cell-specific offset applicable to a specific neighbouring cell.
It is used for evaluating the cell as a candidate for cell re-selection in
idle mode. 
"
::= { neighborListLTECellTableEntry 6 }



neighborListLTECellTblCIO        OBJECT-TYPE
SYNTAX                           QOffsetType
MAX-ACCESS                       read-write
STATUS                           current
DESCRIPTION
"
Cell individual offset applicable to a specific neighbouring cell.
"
::= { neighborListLTECellTableEntry 7 }



neighborListLTECellTblBlacklisted          OBJECT-TYPE
SYNTAX                                     BoolType
MAX-ACCESS                                 read-write
STATUS                                     current
DESCRIPTION
"
Indicates whether this neighbor cell is allowed for UEs as handover target or
not. If true, handover is prohibited towards this cell. If false, handover is
allowed toward this cell. The Blacklisted parameter allows this cell to be
prohibited as a handover target, while still allowing this cell to be
included in the BCCH SIB4 or 5.
"
::= { neighborListLTECellTableEntry 8 }



neighborListMaxUMTSEntries   OBJECT-TYPE
SYNTAX                       Unsigned32
MAX-ACCESS                   read-only
STATUS                       current
DESCRIPTION
"
The maximum number of entries in the neighborListUMTSTable.
"
::= { neighborListInterRATCell 1 }



neighborListUMTSNumberOfEntries   OBJECT-TYPE
SYNTAX                            Unsigned32
MAX-ACCESS                        read-only
STATUS                            current
DESCRIPTION
"
The maximum number of entries in the neighborListUMTSTable.
"
::= { neighborListInterRATCell 2 }



neighborListUMTSTable             OBJECT-TYPE
SYNTAX SEQUENCE OF                NeighborListUMTSTableEntry
MAX-ACCESS                        not-accessible
STATUS                            current
DESCRIPTION
"
Table containing the inter-RAT cell list for UTRA (UMTS) provided by the ACS.
The table contents MAY be added/deleted/modified during operation, in which
case these changes shall be reflected in the broadcast information as soon as
possible.
"
::= { neighborListInterRATCell 3 }



NeighborListUMTSTableEntry ::= SEQUENCE {
        neighborListUMTSTblIndex           Unsigned32,
        neighborListUMTSTblPLMNID          DisplayString,
        neighborListUMTSTblRNCID           Unsigned32,
        neighborListUMTSTblCID             Unsigned32,
        neighborListUMTSTblLAC             Unsigned32,
        neighborListUMTSTblRAC             Unsigned32,
        neighborListUMTSTblUARFCNDL        Unsigned32
}



neighborListUMTSTableEntry     OBJECT-TYPE
SYNTAX                         NeighborListUMTSTableEntry
MAX-ACCESS                     not-accessible
STATUS                         current
DESCRIPTION
"
A row entry in neighborListUMTSTable.
Combination of neighborListUMTSTblPLMNID, neighborListUMTSTblRNCID & neighborListUMTSTblCID forms the key element of each row
"
INDEX { neighborListUMTSTblIndex }
::= { neighborListUMTSTable 1 }



neighborListUMTSTblIndex   OBJECT-TYPE
SYNTAX                     Unsigned32
MAX-ACCESS                 not-accessible
STATUS                     current
DESCRIPTION
"
A unique index identifying q row in neighborListUMTSTable.
"
::= { neighborListUMTSTableEntry 1 }



neighborListUMTSTblPLMNID   OBJECT-TYPE
SYNTAX                      DisplayString
MAX-ACCESS                  read-write
STATUS                      current
DESCRIPTION
"
PLMN ID consists of Mobile Country Code (MCC) and Mobile Network Code (MNC)
[3GPP-TS.23.003], [3GPP-TS.24.008].

Mobile Country Code consists of three digits and uniquely identifies the
country of domicile of the subscriber.

Mobile Network Code consists of two or three digits and identifies the Home
PLMN within a country.

Note : neighborListUMTSTblPLMNID is part of key element of each row
hence SET for neighborListUMTSTblPLMNID parameter is not supported.

"
::= { neighborListUMTSTableEntry 2 }



neighborListUMTSTblRNCID    OBJECT-TYPE
SYNTAX                      Unsigned32 (0..65535)
MAX-ACCESS                  read-write
STATUS                      current
DESCRIPTION
"
RNC-ID of an intra-RAT UMTS neighbor cell. It uniquely identifies an RNC
within a PLMN.

Normally, RNC-ID consists of 12 bits (i.e. a range of [0:4095]). However, if
the value is larger than 4095, then Extended RNC-ID (range of [4096:65535])
is used in RANAP.

The RNC-ID and Extended RNC-ID are combined into a single parameter here as
there is no explicit need to have them separated.

Note : neighborListUMTSTblRNCID is part of key element of each row
hence SET for neighborListUMTSTblRNCID parameter is not supported.
"
::= { neighborListUMTSTableEntry 3 }




neighborListUMTSTblCID      OBJECT-TYPE
SYNTAX                      Unsigned32 (1..65535)
MAX-ACCESS                  read-write
STATUS                      current
DESCRIPTION
"
Cell Identifier (C-id) that identifies a cell within an RNS. This Cell
Identifier together with the controlling RNC (RNC-ID) constitutes the UTRAN
Cell ID (UC-ID) and is used to identify a cell uniquely within UTRAN. C-ID is
either 12-bit or 16-bit value. [Section 6.1.5/3GPP-TS.25.401].

Note : neighborListUMTSTblCID is part of key element of each row
hence SET for neighborListUMTSTblCID parameter is not supported.
"
::= { neighborListUMTSTableEntry 4 }



neighborListUMTSTblLAC       OBJECT-TYPE
SYNTAX                       Unsigned32 (0..65535)
MAX-ACCESS                   read-write
STATUS                       current
DESCRIPTION
"
Location Area Code (LAC). The concatenation of PLMN ID (MCC+MNC) and LAC
uniquely identifies the Location Area ID (LAI).
"
::= { neighborListUMTSTableEntry 5 }



neighborListUMTSTblRAC   OBJECT-TYPE
SYNTAX                   Unsigned32 (0..255)
MAX-ACCESS               read-write
STATUS                   current
DESCRIPTION
"
Routing Area Code (RAC). The concatenation of PLMN ID (MCC+MNC), LAC, and
RAC uniquely identifies the Routing Area ID (RAI).
"
::= { neighborListUMTSTableEntry 6 }



neighborListUMTSTblUARFCNDL   OBJECT-TYPE
SYNTAX                        Unsigned32 (0..16383)
MAX-ACCESS                    read-write
STATUS                        current
DESCRIPTION
"
The DL UTRA Absolute Radio Frequency Channel Number (UARFCN) in an FDD mode
cell. [3GPP-TS.25.433]
"
::= { neighborListUMTSTableEntry 7 }



neighborListInUseMaxLTECellEntries   OBJECT-TYPE
SYNTAX                               Unsigned32
MAX-ACCESS                           read-only
STATUS                               current
DESCRIPTION
"
The maximum number of entries in the neighborListInUseLTECellTable.
"
::= { neighborListInUse 1 }



neighborListInUseLTECellNumberOfEntries   OBJECT-TYPE
SYNTAX                                    Unsigned32
MAX-ACCESS                                read-only
STATUS                                    current
DESCRIPTION
"
The number of entries in the neighborListInUseLTECellTable.
"
::= { neighborListInUse 2 }



neighborListInUseLTECellTable   OBJECT-TYPE
SYNTAX SEQUENCE OF              NeighborListInUseLTECellTableEntry
MAX-ACCESS                      not-accessible
STATUS                          current
DESCRIPTION
"
Table containing the LTE EUTRA (i.e. intra-RAT) cell list.

At most one entry in this table can exist with the same values for PLMNID and
CID.
"
::= { neighborListInUse 3 }



NeighborListInUseLTECellTableEntry ::= SEQUENCE {
        neighborListInUseLTECellTblIndex              Unsigned32,
        neighborListInUseLTECellTblPLMNID             DisplayString,
        neighborListInUseLTECellTblCID                Unsigned32,
        neighborListInUseLTECellTblEUTRACarrierARFCN  Unsigned32,
        neighborListInUseLTECellTblPhyCellID          Unsigned32,
        neighborListInUseLTECellTblQOffset            QOffsetType,
        neighborListInUseLTECellTblBlacklisted        BoolType
}



neighborListInUseLTECellTableEntry     OBJECT-TYPE
SYNTAX                                 NeighborListInUseLTECellTableEntry
MAX-ACCESS                             not-accessible
STATUS                                 current
DESCRIPTION
"
A row in neighborListInUseLTECellTable.
"
INDEX { neighborListInUseLTECellTblIndex }
::= { neighborListInUseLTECellTable 1 }



neighborListInUseLTECellTblIndex   OBJECT-TYPE
SYNTAX                             Unsigned32
MAX-ACCESS                         not-accessible
STATUS                             current
DESCRIPTION
"
A unique index identifying a row in neighborListInUseLTECellTable.
"
::= { neighborListInUseLTECellTableEntry 1 }




neighborListInUseLTECellTblPLMNID   OBJECT-TYPE
SYNTAX                              DisplayString
MAX-ACCESS                          read-only
STATUS                              current
DESCRIPTION
"
PLMN ID consists of Mobile Country Code (MCC) and Mobile Network Code (MNC)
[3GPP-TS.23.003], [3GPP-TS.24.008].

Mobile Country Code consists of three digits and uniquely identifies the
country of domicile of the subscriber.

Mobile Network Code consists of two or three digits and identifies the Home
PLMN within a country.
"
::= { neighborListInUseLTECellTableEntry 2 }



neighborListInUseLTECellTblCID   OBJECT-TYPE
SYNTAX                           Unsigned32 (1..268435455)
MAX-ACCESS                       read-only
STATUS                           current
DESCRIPTION
"
Cell Identity. [Section 6.3.4/3GPP-TS.36.331]. Combination of PLMNID and CID
constitutes the Cell Global ID (CGI).
"
::= { neighborListInUseLTECellTableEntry 3 }



neighborListInUseLTECellTblEUTRACarrierARFCN      OBJECT-TYPE
SYNTAX                                            Unsigned32 (0..65535)
MAX-ACCESS                                        read-only
STATUS                                            current
DESCRIPTION
"
Indicates the ARFCN of this carrier frequency. Corresponds to parameter
dl-CarrierFreq in SIB5 in [Section 6.3.1/3GPP-TS.36.331], and and parameter
NDL in [Section 5.7.3/3GPP-TS.36.101]. If the value of EUTRACarrierARFCN is
the same with the one currently being used by the, then it implies that this
neighbor cell is an intra-frequency cell; otherwise, it is an inter-frequency
cell.
"
::= { neighborListInUseLTECellTableEntry 4 }



neighborListInUseLTECellTblPhyCellID   OBJECT-TYPE
SYNTAX                                 Unsigned32 (0..503)
MAX-ACCESS                             read-only
STATUS                                 current
DESCRIPTION
"
Physical cell ID, as specified in [Section 6.11/3GPP-TS.36.211].
"
::= { neighborListInUseLTECellTableEntry 5 }



neighborListInUseLTECellTblQOffset    OBJECT-TYPE
SYNTAX                                QOffsetType
MAX-ACCESS                            read-only
STATUS                                current
DESCRIPTION
"
Indicate a cell-specific offset applicable to a specific neighbouring cell.
It is used for evaluating the cell as a candidate for cell re-selection in
idle mode.
"
::= { neighborListInUseLTECellTableEntry 6 }



neighborListInUseLTECellTblBlacklisted    OBJECT-TYPE
SYNTAX                                    BoolType
MAX-ACCESS                                read-only
STATUS                                    current
DESCRIPTION
"
Indicates whether this neighbor cell is allowed for UEs as handover target or
not. If true, handover is prohibited towards this cell. If false, handover is
allowed toward this cell. The Blacklisted parameter allows this cell to be
prohibited as a handover target, while still allowing this cell to be included
in the BCCH SIB4 or 5.
"
::= { neighborListInUseLTECellTableEntry 7 }



neighborListInUseMaxUMTSEntries   OBJECT-TYPE
SYNTAX                            Unsigned32
MAX-ACCESS                        read-only
STATUS                            current
DESCRIPTION
"
The maximum number of entries in the neighborListInUseUMTSTable.
"
::= { neighborListInUseInterRATCell 1 }



neighborListInUseUMTSNumberOfEntries   OBJECT-TYPE
SYNTAX                                 Unsigned32
MAX-ACCESS                             read-only
STATUS                                 current
DESCRIPTION
"
The number of entries in the neighborListInUseUMTSTable.
"
::= { neighborListInUseInterRATCell 2 }



NeighborListInUseUMTSTableEntry ::= SEQUENCE {
        neighborListInUseUMTSTblIndex           Unsigned32,
        neighborListInUseUMTSTblPLMNID          DisplayString,
        neighborListInUseUMTSTblRNCID           Unsigned32,
        neighborListInUseUMTSTblCID             Unsigned32,
        neighborListInUseUMTSTblLAC             Unsigned32,
        neighborListInUseUMTSTblRAC             Unsigned32,
        neighborListInUseUMTSTblUARFCNDL        Unsigned32
}



neighborListInUseUMTSTable        OBJECT-TYPE
SYNTAX SEQUENCE OF                NeighborListInUseUMTSTableEntry
MAX-ACCESS                        not-accessible
STATUS                            current
DESCRIPTION
"
Table containing the inter-RAT cell list for UTRA (UMTS) cell.

At most one entry in this table can exist with the same values for PLMNID and
CID.

"
::= { neighborListInUseInterRATCell 3 }



neighborListInUseUMTSTableEntry     OBJECT-TYPE
SYNTAX                              NeighborListInUseUMTSTableEntry
MAX-ACCESS                          not-accessible
STATUS                              current
DESCRIPTION
"
A row in neighborListInUseUMTSTable.
"
INDEX { neighborListInUseUMTSTblIndex }
::= { neighborListInUseUMTSTable 1 }



neighborListInUseUMTSTblIndex   OBJECT-TYPE
SYNTAX                          Unsigned32
MAX-ACCESS                      not-accessible
STATUS                          current
DESCRIPTION
"
A unique index identifying a row in neighborListInUseUMTSTable.
"
::= { neighborListInUseUMTSTableEntry 1 }



neighborListInUseUMTSTblPLMNID   OBJECT-TYPE
SYNTAX                           DisplayString
MAX-ACCESS                       read-only
STATUS                           current
DESCRIPTION
"
PLMN ID consists of Mobile Country Code (MCC) and Mobile Network Code (MNC)
[3GPP-TS.23.003], [3GPP-TS.24.008].

Mobile Country Code consists of three digits and uniquely identifies the
country of domicile of the subscriber.

Mobile Network Code consists of two or three digits and identifies the Home
PLMN within a country.
"
::= { neighborListInUseUMTSTableEntry 2 }



neighborListInUseUMTSTblRNCID    OBJECT-TYPE
SYNTAX                           Unsigned32 (0..65535)
MAX-ACCESS                       read-only
STATUS                           current
DESCRIPTION
"
RNC-ID of an intra-RAT UMTS neighbor cell. It uniquely identifies an RNC
within a PLMN.

Normally, RNC-ID consists of 12 bits (i.e. a range of [0:4095]). However, if
the value is larger than 4095, then Extended RNC-ID (range of [4096:65535])
is used in RANAP.

The RNC-ID and Extended RNC-ID are combined into a single parameter here as
there is no explicit need to have them separated.
"
::= { neighborListInUseUMTSTableEntry 3 }



neighborListInUseUMTSTblCID    OBJECT-TYPE
SYNTAX                         Unsigned32 (1..65535)
MAX-ACCESS                     read-only
STATUS                         current
DESCRIPTION
"
Cell Identifier (C-id) that identifies a cell within an RNS. This Cell
Identifier together with the controlling RNC (RNC-ID) constitutes the UTRAN
Cell ID (UC-ID) and is used to identify a cell uniquely within UTRAN. C-ID is
either 12-bit or 16-bit value.
"
::= { neighborListInUseUMTSTableEntry 4 }



neighborListInUseUMTSTblLAC    OBJECT-TYPE
SYNTAX                         Unsigned32 (0..65535)
MAX-ACCESS                     read-only
STATUS                         current
DESCRIPTION
"
Location Area Code (LAC). The concatenation of PLMN ID (MCC+MNC) and LAC
uniquely identifies the Location Area ID (LAI).
"
::= { neighborListInUseUMTSTableEntry 5 }



neighborListInUseUMTSTblRAC     OBJECT-TYPE
SYNTAX                          Unsigned32 (0..255)
MAX-ACCESS                      read-only
STATUS                          current
DESCRIPTION
"
Routing Area Code (RAC). The concatenation of PLMN ID (MCC+MNC), LAC, and RAC
uniquely identifies the Routing Area ID (RAI).
"
::= { neighborListInUseUMTSTableEntry 6 }



neighborListInUseUMTSTblUARFCNDL   OBJECT-TYPE
SYNTAX                             Unsigned32 (0..16383)
MAX-ACCESS                         read-only
STATUS                             current
DESCRIPTION
"
The DL UTRA Absolute Radio Frequency Channel Number (UARFCN) in an FDD mode
cell.
"
::= { neighborListInUseUMTSTableEntry 7 }




sctpEnable             OBJECT-TYPE
SYNTAX                 BoolType
MAX-ACCESS             read-write
STATUS                 current
DESCRIPTION
"
Enables or disables the whole SCTP object and allows the setup or release of
SCTP associations and their related streams.
These parameters are writable only before the adminState is set to 'unlocked' at startup.
"
::= { sctp 1 }



hbInterval             OBJECT-TYPE
SYNTAX                 Unsigned32 (1..4294967295)
MAX-ACCESS             read-write
STATUS                 current
DESCRIPTION
"
Heartbeat interval in seconds.

The factory default value MUST be 30.
These parameters are writable only before the adminState is set to 'unlocked' at startup.
"
DEFVAL { 30 }
::= { sctp 2 }



maxAssociationRetransmits        OBJECT-TYPE
SYNTAX                           Unsigned32
MAX-ACCESS                       read-write
STATUS                           current
DESCRIPTION
"
Maximum number of consecutive retransmissions to a peer before an endpoint
considers that the peer is unreachable and closes the association.

The factory default value MUST be 10.
These parameters are writable only before the adminState is set to 'unlocked' at startup.
"
DEFVAL { 10 }
::= { sctp 3 }



maxPathRetransmits        OBJECT-TYPE
SYNTAX                    Unsigned32
MAX-ACCESS                read-write
STATUS                    current
DESCRIPTION
"
Maximum retransmission per destination address.

The factory default value MUST be 5.
These parameters are writable only before the adminState is set to 'unlocked' at startup.
"
DEFVAL { 5 }
::= { sctp 4 }



rTOInitial        OBJECT-TYPE
SYNTAX            Unsigned32
MAX-ACCESS        read-write
STATUS            current
DESCRIPTION
"
Initial value for Retransmit timeout in milliseconds. A retransmission time
value of zero means immediate retransmission.

The factory default value MUST be 3000.
These parameters are writable only before the adminState is set to 'unlocked' at startup.
"
DEFVAL { 3000 }
::= { sctp 5 }



rTOMax        OBJECT-TYPE
SYNTAX        Unsigned32
MAX-ACCESS    read-write
STATUS        current
DESCRIPTION
"
Maximum value for Retransmit timeout in milliseconds. A retransmission time
value of zero means immediate retransmission.

The factory default value MUST be 6000.
These parameters are writable only before the adminState is set to 'unlocked' at startup.
"
DEFVAL { 6000 }
::= { sctp 6 }



rTOMin        OBJECT-TYPE
SYNTAX        Unsigned32
MAX-ACCESS    read-write
STATUS        current
DESCRIPTION
"
Minimum value for Retransmit timeout in milliseconds. A retransmission time
value of zero means immediate retransmission.

The value of this parameter MUST be lower than or equal to RTOMax.

The factory default value MUST be 1000.
These parameters are writable only before the adminState is set to 'unlocked' at startup.
"
DEFVAL { 1000 }
::= { sctp 7 }



valCookieLife        OBJECT-TYPE
SYNTAX               Unsigned32
MAX-ACCESS           read-write
STATUS               current
DESCRIPTION
"
Valid cookie life in the 4-way start-up handshake procedure in milliseconds.

The factory default value MUST be 60000.
These parameters are writable only before the adminState is set to 'unlocked' at startup.
"
DEFVAL { 60000 }
::= { sctp 8 }



supportedAlarmNumberOfEntries    OBJECT-TYPE
SYNTAX                           Unsigned32
MAX-ACCESS                       read-only
STATUS                           current
DESCRIPTION
"The number of entries in the SupportedAlarm table."
::= { faultMgmt 1 }


maxCurrentAlarmEntries           OBJECT-TYPE
SYNTAX                           Unsigned32
MAX-ACCESS                       read-only
STATUS                           current
DESCRIPTION
"
The maximum number of entries allowed in the FaultMgmt.CurrentAlarm.{i}.?
table.
"
::= { faultMgmt 2 }


currentAlarmNumberOfEntries      OBJECT-TYPE
SYNTAX                           Unsigned32
MAX-ACCESS                       read-only
STATUS                           current
DESCRIPTION
"
The number of entries in the CurrentAlarm table.
"
::= { faultMgmt 3 }


historyEventNumberOfEntries      OBJECT-TYPE
SYNTAX                           Unsigned32
MAX-ACCESS                       read-only
STATUS                           current
DESCRIPTION
"
The number of entries in the HistoryEvent table.
"
::= { faultMgmt 4 }


expeditedEventNumberOfEntries    OBJECT-TYPE
SYNTAX                           Unsigned32
MAX-ACCESS                       read-only
STATUS                           current
DESCRIPTION
"
The number of entries in the ExpeditedEvent table.
"
::= { faultMgmt 5 }


queuedEventNumberOfEntries    OBJECT-TYPE
SYNTAX                        Unsigned32
MAX-ACCESS                    read-only
STATUS                        current
DESCRIPTION
"
The number of entries in the QueuedEvent table.
"
::= { faultMgmt 6 }




currentAlarmTable       OBJECT-TYPE
SYNTAX SEQUENCE OF      CurrentAlarmTableEntry
MAX-ACCESS              not-accessible
STATUS                  current
DESCRIPTION
"
Contains all currently active alarms (whose FaultMgmt.SupportedAlarm.{i}.
PerceivedSeverity? is not Cleared?).
"
::= { faultMgmt 7 }


CurrentAlarmTableEntry  ::= SEQUENCE {
        currentAlarmTblIndex                   Unsigned32,
        currentAlarmTblAlarmIdentifier         DisplayString,
        currentAlarmTblRaisedTime              DisplayString,
        currentAlarmTblChangedTime             DisplayString,
        currentAlarmTblManagedObjectInstance   DisplayString,
        currentAlarmTblEventType               DisplayString,
        currentAlarmTblProbableCause           DisplayString,
        currentAlarmTblSpecificProblem         DisplayString,
        currentAlarmTblPerceivedSeverity       DisplayString,
        currentAlarmTblAdditionalText          DisplayString,
        currentAlarmTblAdditionalInformation   DisplayString
    }


currentAlarmTableEntry   OBJECT-TYPE
SYNTAX                   CurrentAlarmTableEntry
MAX-ACCESS               not-accessible
STATUS                   current
DESCRIPTION
"
A row in the currentAlarmTable
"
INDEX { currentAlarmTblIndex }
::= { currentAlarmTable 1 }


currentAlarmTblIndex     OBJECT-TYPE
SYNTAX                   Unsigned32
MAX-ACCESS               not-accessible
STATUS                   current
DESCRIPTION
"
Unique index in the currentAlarmTable for each entry
"
::= { currentAlarmTableEntry 1 }


currentAlarmTblAlarmIdentifier     OBJECT-TYPE
SYNTAX                             DisplayString (SIZE(1..64))
MAX-ACCESS                         read-only
STATUS                             current
DESCRIPTION
"
Identifies one Alarm Entry in the Alarm List. This value MUST be uniquely
allocated by the device to the alarm instance during the lifetime of the
individual alarm.
"
::= { currentAlarmTableEntry 2 }


currentAlarmTblRaisedTime     OBJECT-TYPE
SYNTAX                        DisplayString
MAX-ACCESS                    read-only
STATUS                        current
DESCRIPTION
"
Indicates the date and time when the alarm was first raised by the device.
"
::= { currentAlarmTableEntry 3 }


currentAlarmTblChangedTime    OBJECT-TYPE
SYNTAX                        DisplayString
MAX-ACCESS                    read-only
STATUS                        current
DESCRIPTION
"
Indicates the date and time when the alarm was last changed by the device.
"
::= { currentAlarmTableEntry 4 }


currentAlarmTblManagedObjectInstance OBJECT-TYPE
SYNTAX                               DisplayString (SIZE(1..512))
MAX-ACCESS                           read-only
STATUS                               current
DESCRIPTION
"
Specifies the instance of the Informational Object Class in which the alarm
occurred by carrying the Distinguished Name (DN) of this object instance. The
format of the DN is specific to the application that is using this
CurrentAlarm.
"
::= { currentAlarmTableEntry 5 }


currentAlarmTblEventType      OBJECT-TYPE
SYNTAX                        DisplayString (SIZE(1..64))
MAX-ACCESS                    read-only
STATUS                        current
DESCRIPTION
"
Indicates the type of event.
"
::= { currentAlarmTableEntry 6 }


currentAlarmTblProbableCause  OBJECT-TYPE
SYNTAX                        DisplayString (SIZE(1..64))
MAX-ACCESS                    read-only
STATUS                        current
DESCRIPTION
"
Qualifies the alarm and provides further information than EventType.
"
::= { currentAlarmTableEntry 7 }


currentAlarmTblSpecificProblem   OBJECT-TYPE
SYNTAX                           DisplayString (SIZE(1..128))
MAX-ACCESS                       read-only
STATUS                           current
DESCRIPTION
"
Provides further qualification on the alarm beyond EventType and
ProbableCause.

This is vendor defined and will be an empty string if the device doesn't
support inclusion of this information.

"
::= { currentAlarmTableEntry 8 }


currentAlarmTblPerceivedSeverity OBJECT-TYPE
SYNTAX                           DisplayString
MAX-ACCESS                       read-only
STATUS                           current
DESCRIPTION
"
Indicates the relative level of urgency for operator attention, see
[ITU-X.733]. Enumeration of:

  * Critical
  * Major
  * Minor
  * Warning
  * Indeterminate 
"
::= { currentAlarmTableEntry 9 }


currentAlarmTblAdditionalText OBJECT-TYPE
SYNTAX                        DisplayString (SIZE(1..256))
MAX-ACCESS                    read-only
STATUS                        current
DESCRIPTION
"
This provides a textual string which is vendor defined.

This will be an empty string if the device doesn't support inclusion of this
information.
"
::= { currentAlarmTableEntry 10 }


currentAlarmTblAdditionalInformation OBJECT-TYPE
SYNTAX                               DisplayString (SIZE(1..256))
MAX-ACCESS                           read-only
STATUS                               current
DESCRIPTION
"
This contains additional information about the alarm and is vendor defined.
"
::= { currentAlarmTableEntry 11 }


supportedAlarmTable     OBJECT-TYPE
SYNTAX SEQUENCE OF      SupportedAlarmTableEntry
MAX-ACCESS              not-accessible
STATUS                  current
DESCRIPTION
"
Supported Alarm Entries which can be raised by the device.

The instance numbers for this table SHOULD be maintained across firmware
upgrades of the device.
"
::= { faultMgmt 8 }


SupportedAlarmTableEntry  ::= SEQUENCE {
        supportedAlarmTblIndex                   Unsigned32,
        supportedAlarmTblEventType               DisplayString,
        supportedAlarmTblProbableCause           DisplayString,
        supportedAlarmTblSpecificProblem         DisplayString,
        supportedAlarmTblPerceivedSeverity       DisplayString,
        supportedAlarmTblReportingMechanism      DisplayString
    }


supportedAlarmTableEntry OBJECT-TYPE
SYNTAX                   SupportedAlarmTableEntry
MAX-ACCESS               not-accessible
STATUS                   current
DESCRIPTION
"
A row in the supportedAlarmTable
"
INDEX { supportedAlarmTblIndex }
::= { supportedAlarmTable 1 }


supportedAlarmTblIndex     OBJECT-TYPE
SYNTAX                     Unsigned32
MAX-ACCESS                 not-accessible
STATUS                     current
DESCRIPTION
"
Unique index in the currentAlarmTable for each entry
"
::= { supportedAlarmTableEntry 1 }


supportedAlarmTblEventType    OBJECT-TYPE
SYNTAX                        DisplayString (SIZE(1..64))
MAX-ACCESS                    read-only
STATUS                        current
DESCRIPTION
"
Indicates the type of event.
"
::= { supportedAlarmTableEntry 2 }


supportedAlarmTblProbableCause   OBJECT-TYPE
SYNTAX                           DisplayString (SIZE(1..64))
MAX-ACCESS                       read-only
STATUS                           current
DESCRIPTION
"
Qualifies the alarm and provides further information than EventType.
"
::= { supportedAlarmTableEntry 3 }


supportedAlarmTblSpecificProblem   OBJECT-TYPE
SYNTAX                             DisplayString (SIZE(1..128))
MAX-ACCESS                         read-only
STATUS                             current
DESCRIPTION
"
Provides further qualification on the alarm beyond EventType and
ProbableCause.

This is vendor defined and will be an empty string if the device doesn't
support inclusion of this information.

"
::= { supportedAlarmTableEntry 4 }


supportedAlarmTblPerceivedSeverity OBJECT-TYPE
SYNTAX                             DisplayString
MAX-ACCESS                         read-only
STATUS                             current
DESCRIPTION
"
Indicates the relative level of urgency for operator attention, see
[ITU-X.733]. Enumeration of:

  * Critical
  * Major
  * Minor
  * Warning
  * Indeterminate

This will be an empty string if the device doesn't support unique indexing of
the table using PerceivedSeverity.

The string can be set to '*' to indicate the default case if only a subset of
PerceivedSeverity are to be contained within the table.
"
::= { supportedAlarmTableEntry 5 }


supportedAlarmTblReportingMechanism  OBJECT-TYPE
SYNTAX                               DisplayString
MAX-ACCESS                           read-write
STATUS                               current
DESCRIPTION
"
Indicates the reporting mechanism setting of the alarm. Enumeration of:

    0 Expedited (The device inserts the alarm into the
      FaultMgmt.ExpeditedEvent.{i}.? table and the
      FaultMgmt.ExpeditedEvent.{i}.? table)
    1 Queued (The device inserts the alarm into the
      FaultMgmt.QueuedEvent.{i}.? table and the FaultMgmt.QueuedEvent.{i}.?
      table)
    2 Logged (The device inserts the alarm into the
      FaultMgmt.HistoryEvent.{i}.? table)
    3 Disabled (The device ignores the alarm) 
"
::= { supportedAlarmTableEntry 6 }


historyEventTable       OBJECT-TYPE
SYNTAX SEQUENCE OF      HistoryEventTableEntry
MAX-ACCESS              not-accessible
STATUS                  current
DESCRIPTION
"
Alarm events added or updated in FaultMgmt.CurrentAlarm.{i}.? are
simultaneously entered into the this table. This table also contains alarm
clearing events.
"
::= { faultMgmt 9 }

HistoryEventTableEntry  ::= SEQUENCE {
        historyEventTblIndex                   Unsigned32,
        historyEventTblEventTime               DisplayString,
        historyEventTblAlarmIdentifier         DisplayString,
        historyEventTblNotificationType        DisplayString,
        historyEventTblManagedObjectInstance   DisplayString,
        historyEventTblEventType               DisplayString,
        historyEventTblProbableCause           DisplayString,
        historyEventTblSpecificProblem         DisplayString,
        historyEventTblPerceivedSeverity       DisplayString,
        historyEventTblAdditionalText          DisplayString,
        historyEventTblAdditionalInformation   DisplayString
    }


historyEventTableEntry   OBJECT-TYPE
SYNTAX                   HistoryEventTableEntry
MAX-ACCESS               not-accessible
STATUS                   current
DESCRIPTION
"
A row in the historyEventTable
"
INDEX { historyEventTblIndex }
::= { historyEventTable 1 }


historyEventTblIndex     OBJECT-TYPE
SYNTAX                   Unsigned32
MAX-ACCESS               not-accessible
STATUS                   current
DESCRIPTION
"
Unique index in the historyEventTable for each entry
"
::= { historyEventTableEntry 1 }


historyEventTblEventTime     OBJECT-TYPE
SYNTAX                       DisplayString
MAX-ACCESS                   read-only
STATUS                       current
DESCRIPTION
"
Indicates the date and time when the alarm event occurs.
"
::= { historyEventTableEntry 2 }


historyEventTblAlarmIdentifier  OBJECT-TYPE
SYNTAX                          DisplayString (SIZE(1..64))
MAX-ACCESS                      read-only
STATUS                          current
DESCRIPTION
"
Identifies one Alarm Entry in the Alarm List. This value MUST be uniquely
allocated by the device to the alarm instance during the lifetime of the
individual alarm.
"
::= { historyEventTableEntry 3 }


historyEventTblNotificationType OBJECT-TYPE
SYNTAX                          DisplayString
MAX-ACCESS                      read-only
STATUS                          current
DESCRIPTION
"
Indicates the reason for the specific alarm notification event. Enumeration
of:

  * NewAlarm
  * ChangedAlarm
  * ClearedAlarm 
"
::= { historyEventTableEntry 4 }


historyEventTblManagedObjectInstance OBJECT-TYPE
SYNTAX                               DisplayString (SIZE(1..512))
MAX-ACCESS                           read-only
STATUS                               current
DESCRIPTION
"
Specifies the instance of the Informational Object Class in which the alarm
occurred by carrying the Distinguished Name (DN) of this object instance. The
format of the DN is specific to the application that is using this
HistoryEvent.
"
::= { historyEventTableEntry 5 }


historyEventTblEventType OBJECT-TYPE
SYNTAX                   DisplayString (SIZE(1..64))
MAX-ACCESS               read-only
STATUS                   current
DESCRIPTION
"
Indicates the type of event.
"
::= { historyEventTableEntry 6 }


historyEventTblProbableCause  OBJECT-TYPE
SYNTAX                        DisplayString (SIZE(1..64))
MAX-ACCESS                    read-only
STATUS                        current
DESCRIPTION
"
Qualifies the alarm and provides further information than EventType.
"
::= { historyEventTableEntry 7 }


historyEventTblSpecificProblem   OBJECT-TYPE
SYNTAX                           DisplayString (SIZE(1..128))
MAX-ACCESS                       read-only
STATUS                           current
DESCRIPTION
"
Provides further qualification on the alarm beyond EventType and
ProbableCause.

This is vendor defined and will be an empty string if the device doesn't
support inclusion of this information.

"
::= { historyEventTableEntry 8 }


historyEventTblPerceivedSeverity OBJECT-TYPE
SYNTAX                           DisplayString
MAX-ACCESS                       read-only
STATUS                           current
DESCRIPTION
"
Indicates the relative level of urgency for operator attention, see
[ITU-X.733]. Enumeration of:

  * Critical
  * Major
  * Minor
  * Warning
  * Indeterminate 
"
::= { historyEventTableEntry 9 }


historyEventTblAdditionalText OBJECT-TYPE
SYNTAX                        DisplayString (SIZE(1..256))
MAX-ACCESS                    read-only
STATUS                        current
DESCRIPTION
"
This provides a textual string which is vendor defined.

This will be an empty string if the device doesn't support inclusion of this
information.
"
::= { historyEventTableEntry 10 }


historyEventTblAdditionalInformation OBJECT-TYPE
SYNTAX                               DisplayString (SIZE(1..256))
MAX-ACCESS                           read-only
STATUS                               current
DESCRIPTION
"
This contains additional information about the alarm and is vendor defined.
"
::= { historyEventTableEntry 11 }


expeditedEventTable     OBJECT-TYPE
SYNTAX SEQUENCE OF      ExpeditedEventTableEntry
MAX-ACCESS              not-accessible
STATUS                  current
DESCRIPTION
"
Alarm events added or updated in FaultMgmt.CurrentAlarm.{i}.? are
simultaneously entered into the this table if their corresponding entry in
FaultMgmt.SupportedAlarm.{i}.? has
FaultMgmt.SupportedAlarm.{i}.ReportingMechanism? set to 0 Expedited?. This
table also contains alarm clearing events. 
"
::= { faultMgmt 10 }

ExpeditedEventTableEntry  ::= SEQUENCE {
        expeditedEventTblIndex                   Unsigned32,
        expeditedEventTblEventTime               DisplayString,
        expeditedEventTblAlarmIdentifier         DisplayString,
        expeditedEventTblNotificationType        DisplayString,
        expeditedEventTblManagedObjectInstance   DisplayString,
        expeditedEventTblEventType               DisplayString,
        expeditedEventTblProbableCause           DisplayString,
        expeditedEventTblSpecificProblem         DisplayString,
        expeditedEventTblPerceivedSeverity       DisplayString,
        expeditedEventTblAdditionalText          DisplayString,
        expeditedEventTblAdditionalInformation   DisplayString
    }


expeditedEventTableEntry OBJECT-TYPE
SYNTAX                   ExpeditedEventTableEntry
MAX-ACCESS               not-accessible
STATUS                   current
DESCRIPTION
"
A row in the expeditedEventTable
"
INDEX { expeditedEventTblIndex }
::= { expeditedEventTable 1 }


expeditedEventTblIndex     OBJECT-TYPE
SYNTAX                     Unsigned32
MAX-ACCESS                 not-accessible
STATUS                     current
DESCRIPTION
"
Unique index in the expeditedEventTable for each entry
"
::= { expeditedEventTableEntry 1 }


expeditedEventTblEventTime     OBJECT-TYPE
SYNTAX                         DisplayString
MAX-ACCESS                     read-only
STATUS                         current
DESCRIPTION
"
Indicates the date and time when the alarm event occurs.
"
::= { expeditedEventTableEntry 2 }


expeditedEventTblAlarmIdentifier  OBJECT-TYPE
SYNTAX                            DisplayString (SIZE(1..64))
MAX-ACCESS                        read-only
STATUS                            current
DESCRIPTION
"
Identifies one Alarm Entry in the Alarm List. This value MUST be uniquely
allocated by the device to the alarm instance during the lifetime of the
individual alarm.
"
::= { expeditedEventTableEntry 3 }


expeditedEventTblNotificationType  OBJECT-TYPE
SYNTAX                             DisplayString
MAX-ACCESS                         read-only
STATUS                             current
DESCRIPTION
"
Indicates the reason for the specific alarm notification event. Enumeration
of:

  * NewAlarm
  * ChangedAlarm
  * ClearedAlarm 
"
::= { expeditedEventTableEntry 4 }


expeditedEventTblManagedObjectInstance OBJECT-TYPE
SYNTAX                                 DisplayString (SIZE(1..512))
MAX-ACCESS                             read-only
STATUS                                 current
DESCRIPTION
"
Specifies the instance of the Informational Object Class in which the alarm
occurred by carrying the Distinguished Name (DN) of this object instance. The
format of the DN is specific to the application that is using this
ExpeditedEvent.
"
::= { expeditedEventTableEntry 5 }


expeditedEventTblEventType OBJECT-TYPE
SYNTAX                     DisplayString (SIZE(1..64))
MAX-ACCESS                 read-only
STATUS                     current
DESCRIPTION
"
Indicates the type of event.
"
::= { expeditedEventTableEntry 6 }


expeditedEventTblProbableCause  OBJECT-TYPE
SYNTAX                          DisplayString (SIZE(1..64))
MAX-ACCESS                      read-only
STATUS                          current
DESCRIPTION
"
Qualifies the alarm and provides further information than EventType.
"
::= { expeditedEventTableEntry 7 }


expeditedEventTblSpecificProblem   OBJECT-TYPE
SYNTAX                             DisplayString (SIZE(1..128))
MAX-ACCESS                         read-only
STATUS                             current
DESCRIPTION
"
Provides further qualification on the alarm beyond EventType and
ProbableCause.

This is vendor defined and will be an empty string if the device doesn't
support inclusion of this information.

"
::= { expeditedEventTableEntry 8 }


expeditedEventTblPerceivedSeverity OBJECT-TYPE
SYNTAX                             DisplayString
MAX-ACCESS                         read-only
STATUS                             current
DESCRIPTION
"
Indicates the relative level of urgency for operator attention, see
[ITU-X.733]. Enumeration of:

  * Critical
  * Major
  * Minor
  * Warning
  * Indeterminate 
"
::= { expeditedEventTableEntry 9 }


expeditedEventTblAdditionalText OBJECT-TYPE
SYNTAX                          DisplayString (SIZE(1..256))
MAX-ACCESS                      read-only
STATUS                          current
DESCRIPTION
"
This provides a textual string which is vendor defined.

This will be an empty string if the device doesn't support inclusion of this
information.
"
::= { expeditedEventTableEntry 10 }


expeditedEventTblAdditionalInformation OBJECT-TYPE
SYNTAX                                 DisplayString (SIZE(1..256))
MAX-ACCESS                             read-only
STATUS                                 current
DESCRIPTION
"
This contains additional information about the alarm and is vendor defined.
"
::= { expeditedEventTableEntry 11 }


queuedEventTable     OBJECT-TYPE
SYNTAX SEQUENCE OF   QueuedEventTableEntry
MAX-ACCESS           not-accessible
STATUS               current
DESCRIPTION
"
Alarm events added or updated in FaultMgmt.CurrentAlarm.{i}.? are
simultaneously entered into the this table if their corresponding entry in
FaultMgmt.SupportedAlarm.{i}.? has
FaultMgmt.SupportedAlarm.{i}.ReportingMechanism? set to 1 Queued?. This table
also contains alarm clearing events. 
"
::= { faultMgmt 11 }

QueuedEventTableEntry  ::= SEQUENCE {
        queuedEventTblIndex                   Unsigned32,
        queuedEventTblEventTime               DisplayString,
        queuedEventTblAlarmIdentifier         DisplayString,
        queuedEventTblNotificationType        DisplayString,
        queuedEventTblManagedObjectInstance   DisplayString,
        queuedEventTblEventType               DisplayString,
        queuedEventTblProbableCause           DisplayString,
        queuedEventTblSpecificProblem         DisplayString,
        queuedEventTblPerceivedSeverity       DisplayString,
        queuedEventTblAdditionalText          DisplayString,
        queuedEventTblAdditionalInformation   DisplayString
    }


queuedEventTableEntry OBJECT-TYPE
SYNTAX                   QueuedEventTableEntry
MAX-ACCESS               not-accessible
STATUS                   current
DESCRIPTION
"
A row in the queuedEventTable
"
INDEX { queuedEventTblIndex }
::= { queuedEventTable 1 }


queuedEventTblIndex     OBJECT-TYPE
SYNTAX                  Unsigned32
MAX-ACCESS              not-accessible
STATUS                  current
DESCRIPTION
"
Unique index in the queuedEventTable for each entry
"
::= { queuedEventTableEntry 1 }


queuedEventTblEventTime     OBJECT-TYPE
SYNTAX                      DisplayString
MAX-ACCESS                  read-only
STATUS                      current
DESCRIPTION
"
Indicates the date and time when the alarm event occurs.
"
::= { queuedEventTableEntry 2 }


queuedEventTblAlarmIdentifier     OBJECT-TYPE
SYNTAX                            DisplayString (SIZE(1..64))
MAX-ACCESS                        read-only
STATUS                            current
DESCRIPTION
"
Identifies one Alarm Entry in the Alarm List. This value MUST be uniquely
allocated by the device to the alarm instance during the lifetime of the
individual alarm.
"
::= { queuedEventTableEntry 3 }


queuedEventTblNotificationType  OBJECT-TYPE
SYNTAX                          DisplayString
MAX-ACCESS                      read-only
STATUS                          current
DESCRIPTION
"
Indicates the reason for the specific alarm notification event. Enumeration
of:

  * NewAlarm
  * ChangedAlarm
  * ClearedAlarm 
"
::= { queuedEventTableEntry 4 }


queuedEventTblManagedObjectInstance OBJECT-TYPE
SYNTAX                              DisplayString (SIZE(1..512))
MAX-ACCESS                          read-only
STATUS                              current
DESCRIPTION
"
Specifies the instance of the Informational Object Class in which the alarm
occurred by carrying the Distinguished Name (DN) of this object instance. The
format of the DN is specific to the application that is using this
ExpeditedEvent.
"
::= { queuedEventTableEntry 5 }


queuedEventTblEventType         OBJECT-TYPE
SYNTAX                          DisplayString (SIZE(1..64))
MAX-ACCESS                      read-only
STATUS                          current
DESCRIPTION
"
Indicates the type of event.
"
::= { queuedEventTableEntry 6 }


queuedEventTblProbableCause  OBJECT-TYPE
SYNTAX                       DisplayString (SIZE(1..64))
MAX-ACCESS                   read-only
STATUS                       current
DESCRIPTION
"
Qualifies the alarm and provides further information than EventType.
"
::= { queuedEventTableEntry 7 }


queuedEventTblSpecificProblem   OBJECT-TYPE
SYNTAX                          DisplayString (SIZE(1..128))
MAX-ACCESS                      read-only
STATUS                          current
DESCRIPTION
"
Provides further qualification on the alarm beyond EventType and
ProbableCause.

This is vendor defined and will be an empty string if the device doesn't
support inclusion of this information.

"
::= { queuedEventTableEntry 8 }


queuedEventTblPerceivedSeverity OBJECT-TYPE
SYNTAX                          DisplayString
MAX-ACCESS                      read-only
STATUS                          current
DESCRIPTION
"
Indicates the relative level of urgency for operator attention, see
[ITU-X.733]. Enumeration of:

  * Critical
  * Major
  * Minor
  * Warning
  * Indeterminate 
"
::= { queuedEventTableEntry 9 }


queuedEventTblAdditionalText OBJECT-TYPE
SYNTAX                       DisplayString (SIZE(1..256))
MAX-ACCESS                   read-only
STATUS                       current
DESCRIPTION
"
This provides a textual string which is vendor defined.

This will be an empty string if the device doesn't support inclusion of this
information.
"
::= { queuedEventTableEntry 10 }


queuedEventTblAdditionalInformation OBJECT-TYPE
SYNTAX                              DisplayString (SIZE(1..256))
MAX-ACCESS                          read-only
STATUS                              current
DESCRIPTION
"
This contains additional information about the alarm and is vendor defined.
"
::= { queuedEventTableEntry 11 }


-- TRAPS DEFINITIONS
-- =================


trapIdentifier  OBJECT-TYPE
SYNTAX          DisplayString (SIZE(1..64))
MAX-ACCESS      accessible-for-notify
STATUS          current
DESCRIPTION
"
A unique identifier for a trap object.
"
::= { enbTrapParams 1 }


trapEventTime  OBJECT-TYPE
SYNTAX          DisplayString
MAX-ACCESS      accessible-for-notify
STATUS          current
DESCRIPTION
"
Indicates the date and time when the trap was first occurred.
"
::= { enbTrapParams 2 }


trapNotificationType  OBJECT-TYPE
SYNTAX           DisplayString
MAX-ACCESS       accessible-for-notify
STATUS           current
DESCRIPTION
"
Indicates the reason for the specific alarm notification event.
Enumeration of:
    * New Alarm
    * ChangedAlarm
    * ClearedAlarm
"
::= { enbTrapParams 3 }


trapManagedObjectInstance  OBJECT-TYPE
SYNTAX                     DisplayString (SIZE(1..512))
MAX-ACCESS                 accessible-for-notify
STATUS                     current
DESCRIPTION
"
Specifies the instance of the Informational Object Class in which the trap
occurred by carrying the Distinguished Name (DN) of this object instance.
"
::= { enbTrapParams 4 }



trapEventType  OBJECT-TYPE
SYNTAX         DisplayString (SIZE(1..64))
MAX-ACCESS     accessible-for-notify
STATUS         current
DESCRIPTION
"
Indicates the type of event.
"
::= { enbTrapParams 5 }




trapProbableCause  OBJECT-TYPE
SYNTAX             DisplayString (SIZE(1..64))
MAX-ACCESS         accessible-for-notify
STATUS             current
DESCRIPTION
"
Qualifies the trap and provides further information than EventType.
"
::= { enbTrapParams 6 }




trapSpecificProblem  OBJECT-TYPE
SYNTAX               DisplayString (SIZE(1..128))
MAX-ACCESS           accessible-for-notify
STATUS               current
DESCRIPTION
"
Provides further qualification on the trap beyond EventType and
ProbableCause.
"
::= { enbTrapParams 7 }




trapPerceivedSeverity  OBJECT-TYPE
SYNTAX                 DisplayString
MAX-ACCESS             accessible-for-notify
STATUS                 current
DESCRIPTION
"
Indicates the relative level of urgency for operator attention.
Enumeration of:

  * Critical
  * Major
  * Minor
  * Warning
  * Indeterminate 
"
::= { enbTrapParams 8 }




trapAdditionalText     OBJECT-TYPE
SYNTAX                 DisplayString (SIZE(1..256))
MAX-ACCESS             accessible-for-notify
STATUS                 current
DESCRIPTION
"
This provides a textual string which is vendor defined.
"
::= { enbTrapParams 9 }




trapAdditionalInformation     OBJECT-TYPE
SYNTAX                        DisplayString (SIZE(1..256))
MAX-ACCESS                    accessible-for-notify
STATUS                        current
DESCRIPTION
"
This contains additional information about the trap and is vendor defined.
"
::= { enbTrapParams 10 }

 

rrcProvisioningFailureAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  current

DESCRIPTION
"
This trap is raised when provisioning of RRC layer fails.
"
::= { software 1 }

 

s1apProvisioningFailureAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  current

DESCRIPTION
"
This trap is raised when provisioning of S1AP layer fails.
"
::= { software 2 }

 

criticalConfigurationPlanError      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  current

DESCRIPTION
"
Critical configuration plan error.
"
::= { software 3 }

 

timerStartFailedAlarm   NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  current

DESCRIPTION
"
This trap is raised when there is a failure in starting a timer.
"
::= { software 4 }

 

timerStopFailedAlarm    NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  current

DESCRIPTION
"
This trap is raised if there is a failure in stopping a timer.
"
::= { software 5 }

 

sendMsgFailedAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  current

DESCRIPTION
"
A trap raised when message sending is failed.
"
::= { software 6 }

 

recvMsgFailedAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  current

DESCRIPTION
"
A trap raised when a receive failure occurs.
"
::= { software 7 }

 

memAllocFailedAlarm     NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  current

DESCRIPTION
"
This trap is raised when there is a failure in memory allocation.
"
::= { software 8 }

 

memFreeFailedAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  current

DESCRIPTION
"
A trap raised when freeing of memory block fails.
"
::= { software 9 }

 

oamPMDataUploadFailure      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  current

DESCRIPTION
"
This trap is raised for failed PM data upload in OAM.
"
::= { software 10 }

 

oamConfigFilePersistenceFailure      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  current

DESCRIPTION
"
This trap is raised for failure in persistence in the OAM config files.
"
::= { software 11 }

 

oamImageDownloadFailure      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  current

DESCRIPTION
"
This trap is raised for failure in image download.
"
::= { software 12 }

 

oamLogArchiveFailure      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  current

DESCRIPTION
"
This trap is raised for failure in log archive.
"
::= { software 13 }

 

oamLogArchiveUploadFailure      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  current

DESCRIPTION
"
This trap is raised for failure in upload of OAM log archive.
"
::= { software 14 }

 

oamPkgIntegrityCheckFailure NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  current

DESCRIPTION
"
This trap is raised for failure in Software Download Manager
"
::= { software 15 }

 

oamPDCPSecurityEngineError NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  current

DESCRIPTION
"
This trap is raised for failure in L2 software
"
::= { software 16 }

oamLayerStartupFailureAlarm NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  current

DESCRIPTION
"
This trap is raised by OAM when failure occurs in the startup procedure of eNB Layer.
"
::= { software 17 }


hmResponseNotRecvdAlarm NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  current

DESCRIPTION
"
This trap is raised by OAM when the HM module fails to receive HM indications
"
::= { software 18 }

macPhyOAMErrorMsgInvalidState  NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  current

DESCRIPTION
"
This trap is raised by OAM when the receiver message is not valid in PHY's current state
"
::= { software 19 }

macPhyOAMErrorSFNOutofsyncByMoreThanThreshold  NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  current

DESCRIPTION
"
This trap is raised by OAM when the DL config req is received with a different 
SFN than the PHY expected. This error is received for more than a threshold
"
::= { software 20 }

macPhyOAMErrMsgBCHmissing  NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  current

DESCRIPTION
"
This trap is raised by OAM when BCH PDU was expected in the 
DL Config request message for a subframe but it was not present
"
::= { software 21 }

macPhyOAMerrMsgHiErr  NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  current

DESCRIPTION
"
This trap is raised by OAM when an error is received in HI_DCI request
"
::= { software 22 }

pciConflictNotification  NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  current

DESCRIPTION
"
This trap is raised by OAM when PCI conflict is detected at SON
"
::= { software 23 }

pciConfusionNotification  NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  current

DESCRIPTION
"
This trap is raised by OAM when PCI confusion is detected at SON
"
::= { software 24 }
m2apProvisioningFailureAlarm NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  current

DESCRIPTION
"
This trap is raised when provisioning of M2AP layer fails.
"
::= { software 25 }



embmsNotSupportedAlarm NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  current

DESCRIPTION
"
This trap is raised by OAM if eMBMS not supported by PHY.
"
::= { software 26 }


rrcSCTPAssociationFailureAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  current

DESCRIPTION
"
This trap is raised when SCTP association in the RRC layer fails.
"
--SPR 21845 Start
::= { software 25 }

 

ABSPatternNotFoundForLowLoadAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  current

DESCRIPTION
"
This trap is raised for ABS Pattern Not Found For Low Load Level.
"
::= { software 26 }

 

ABSPatternNotFoundForMidLoadAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  current

DESCRIPTION
"
This trap is raised for ABS Pattern Not Found For Mid Load Level.
"
::= { software 27 }

 

ABSPatternNotFoundForHighloadLoadAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  current

DESCRIPTION
"
This trap is raised for ABS Pattern Not Found For High Load Level.
"
::= { software 28 }

 

ABSPatternNotFoundForOverloadLoadAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  current

DESCRIPTION
"
This trap is raised for  ABS Pattern Not Found For Over Load Level.
"
::= { software 29 }

 

ABSPatternFoundForLowloadLoadAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  current

DESCRIPTION
"
"This trap is raised for  ABS Pattern Found For Low Load level. This is raised as clearing alarm for ABS Pattern not found for Low load level.
"
::= { software 30 }

 

ABSPatternFoundForMidloadLoadAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  current

DESCRIPTION
"
"This trap is raised for  ABS Pattern Found For Mid Load level. This is raised as clearing alarm for ABS Pattern not found for Mid load level.
"
::= { software 31 }

 

ABSPatternFoundForHighloadLoadAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  current

DESCRIPTION
"
"This trap is raised for  ABS Pattern Found For High Load level. This is raised as a clearing alarm for ABS Pattern not found for High load level.
"
::= { software 32 }

 

ABSPatternFoundForOverloadLoadAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  current

DESCRIPTION
"
"This trap is raised for  ABS Pattern Found For Over Load level. This is raised as clearing alarm for ABS Pattern not found for Over load level.
"
--SPR 21845 End
::= { link 1 }

 

rrcSCTPAssociationRecoveryAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  current

DESCRIPTION
"
This trap is raised when SCTP association in the RRC layer recovers.
"
::= { link 2 }

 

rrcS1APConnectionFailureAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  current

DESCRIPTION
"
This trap is raised when the connection b/w RRC and S1AP fails.
"
::= { link 3 }

 

rrcS1APConnectionSuccessAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  current

DESCRIPTION
"
This trap is raised when the connection b/w RRC and S1AP succeeds.
"
::= { link 4 }
 

x2apAssociationLinkUpAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  current

DESCRIPTION
"
This trap is raised when SON sends a X2ap link-up indication.
"
::= { link 5 }
 

x2apAssociationLinkDownAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  current

DESCRIPTION
"
This trap is raised when SON sends a X2ap link-down indication.
"
::= { link 6 }
 


egtpuSGWConnectionFailureAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  current

DESCRIPTION
"
This trap is raised when EGTPU sends a S1U link-failure indication.
"
::= { link 7 }
 


egtpuSGWConnectionRecoveryAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  current

DESCRIPTION
"
This trap is raised when EGTPU sends a S1U link-recovery indication.
"
::= { link 8 }

sctpAssocFailAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  current

DESCRIPTION
"
This trap is raised when M2AP not able to connect with MCE.
"
::= { link 9 }



rrcM2APConnSuccAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  current

DESCRIPTION
"
This trap is raised when M2AP setup with MCE fails.
"
::= { link 10 }



rrcM2APConnFailAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  current

DESCRIPTION
"
This trap is raised when M2 link b/w M2AP and MCE goes down due to SCTP abort.
"
::= { link 11 }



m2apProvFailureAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  current

DESCRIPTION
"
This trap is raised when M2 link b/w M2AP and MCE goes down due to SCTP abort.
"
::= { link 12 }



embmsNotSupportedAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  current

DESCRIPTION
"
This trap is raised when M2 link b/w M2AP and MCE goes down due to SCTP abort.
"
::= { link 13 }


slaveLowSignalAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
This trap is raised for Slave Link Low Signal level.
"
--SPR 21845 Start
::= { link 9 }

 

rrcS1APResetAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  current

DESCRIPTION
"
This trap is raised when S1AP reset procedure is triggered.
"
::= { link 10 }

 

configurationFailureAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  current

DESCRIPTION
"
This trap is raised for Configuration failure.
"
::= { link 11 }

 

X2apPeereNBResetAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  current

DESCRIPTION
"
This trap is raised for peer eNB Reset.
"
::= { link 12 }

 

X2apSelfResetAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  current

DESCRIPTION
"
This trap is raised for X2AP Self Reset.
"
::= { link 13 }

 

rrcX2apConnectionFailureAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  current

DESCRIPTION
"
This trap is raised for rrc x2ap connection failure.
"
::= { link 14 }

 

rrcX2apConnectionSuccessAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  current

DESCRIPTION
"
This trap is raised for rrc X2AP Connection Success.
"
::= { link 15 }

 

rrcS1apErrorEndicationAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  current

DESCRIPTION
"
This trap is raised for rrc s1ap error endication.
"
::= { link 16 }

 

rrcX2apErrorEndicationAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  current

DESCRIPTION
"
This trap is raised for rrc x2ap error endication.
"
--SPR 21845 End
::= { rrhTraps 1 }

 

slaveLOFAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
This trap is raised for Slave Link Loss of Framing.
"
::= { rrhTraps 2 }

 

slaveLOSAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
This trap is raised for Slave Link Loss of Signal.
"
::= { rrhTraps 3 }

 

slaveTransFailAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
This trap is raised for Slave Link Transceiver Fail.
"
::= { rrhTraps 4 }

 

slaveRAIAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
This trap is raised for Slave Link Remote Alarm Ind.
"
::= { rrhTraps 5 }

 

slaveSDIAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
This trap is raised for Slave Link SAP Defect.
"
::= { rrhTraps 6 }

 

masterLowSignalAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
This trap is raised for Master Link Low Signal level.
"
::= { rrhTraps 7 }

 

masterLOFAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
This trap is raised for Master Link Loss of Framing.
"
::= { rrhTraps 8 }

 

masterLOSAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
This trap is raised for Master Link Loss of Signal.
"
::= { rrhTraps 9 }

 

masterTRxFailAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
This trap is raised for Master Link Transceiver Fail.
"
::= { rrhTraps 10 }

 

tx2GainWarning      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
This trap is raised for Tx2 Gain Warning.
"
::= { rrhTraps 11 }

 

masterRAIAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
This trap is raised for Master Link Remote Alarm Indication.
"
::= { rrhTraps 12 }

 

masterSDIAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
This trap is raised for Master Link SAP Defect.
"
::= { rrhTraps 13 }

 

cellBlockRequested      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
This trap is raised for Cell Block request.
"
::= { rrhTraps 14 }

 

commsFailAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
This trap is raised for communications failure.
"
::= { rrhTraps 15 }

 

underTempAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
This trap is raised for Temperature being too low.
"
::= { rrhTraps 16 }

 

warmUPAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
This trap is raised when Unit is warming up.
"
::= { rrhTraps 17 }

 

tempWarningAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
This trap is raised when Temperature is too high.
"
::= { rrhTraps 18 }

 

tempCriticalAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
This trap is raised when there is unacceptable temperature.
"
::= { rrhTraps 19 }

 

tx1VSWRLevel2Alarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
RRH Alarm: Tx1 VSWR Level 2
"
::= { rrhTraps 20 }

 

tx2IPOverdriveAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
RRH Alarm: Tx2 Digital Input Overdrive.
"
::= { rrhTraps 21 }

 

selfTestPartialAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
RRH Alarm: Self Test Partial Failure
"
::= { rrhTraps 22 }
 


selfTestCriticalAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
RRH Alarm: Self Test Critical Failure
"
::= { rrhTraps 23 }
 


initFailAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
RRH Alarm: Initialization Failure
"
::= { rrhTraps 24 }
 


softwareFailAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
RRH Alarm: Software Failure
"
::= { rrhTraps 25 }
 


msgThrottleAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
RRH Alarm: Message Throttling
"
::= { rrhTraps 26 }
 


tx2EquipmentFailAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
RRH Alarm: Tx2 Equipment Failure
"
::= { rrhTraps 27 }
 


signalQualityAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
RRH Alarm: Linearization failed
"
::= { rrhTraps 28 }
 


rxFailAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
RRH Alarm: Rx LO PLL unlocked
"
::= { rrhTraps 29 }
 


tx1GainWarning      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
RRH Alarm: Tx 1 Gain limit exceded
"
::= { rrhTraps 30 }
 


tx1TxFailAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
RRH Alarm: Transmitter 1 Failure
"
::= { rrhTraps 31 }
 


tx1GainFailAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
RRH Alarm: Tx 1 Gain Control Failed
"
::= { rrhTraps 32 }
 


tx1OpOverdriveAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
RRH Alarm: Tx 1 Output Overdrive
"
::= { rrhTraps 33 }
 


rx1FailAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
RRH Alarm: Receiver 1 Failure
"
::= { rrhTraps 34 }
 


rx2FailAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
RRH Alarm: Receiver 2 Failure
"
::= { rrhTraps 35 }
 


rxDivImbAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
RRH Alarm: Rx Diversity Imbalance failed
"
::= { rrhTraps 36 }
 


tx1VSWRLevel1Alarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
RRH Alarm: Tx 1 VSWR Level 1 Alarm
"
::= { rrhTraps 37 }
 


tx1EquipmentFailAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
RRH Alarm: Tx1 Equipment Failure
"
::= { rrhTraps 38 }
 


ipVoltageFailAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
RRH Alarm: Input Voltage failure
"
::= { rrhTraps 39 }
 


powerConvertorAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
RRH Alarm: Power Convertor Failure
"
::= { rrhTraps 40 }
 


loopbackReqAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
RRH Alarm: Loopback Requested
"
::= { rrhTraps 41 }
 


cMTimerExpiredAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
RRH Alarm: C & M Timer Expired
"
::= { rrhTraps 42 }
 


tx2VSWRLevel1Alarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
RRH Alarm: Tx 2 VSWR Level 1 Alarm
"
::= { rrhTraps 43 }
 


clockFailAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
RRH Alarm: Clock Synchronization Failed
"
::= { rrhTraps 44 }
 


rfSynthFailAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
RRH Alarm: Transmit LO PLL unlocked
"
::= { rrhTraps 45 }
 


tx1IPOverdriveAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
RRH Alarm: Tx1 Digital Input Overdrive
"
::= { rrhTraps 46 }
 


ttlna1FailAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
RRH Alarm: TTLNA 1 Critical Failure
"
::= { rrhTraps 47 }
 


ttlna2FailAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
RRH Alarm: TTLNA 2 Critical Failure
"
::= { rrhTraps 48 }
 


accessPanelOpenAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
RRH Alarm: Access panel Open
"
::= { rrhTraps 49 }
 


securityAlarmAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
RRH Alarm: Security Alarm
"
::= { rrhTraps 50 }
 


rx1VSWRAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
RRH Alarm: Rx 1 VSWR Alarm
"
::= { rrhTraps 51 }
 


rx2VSWRAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
RRH Alarm: Rx 2 VSWR Alarm
"
::= { rrhTraps 52 }
 


rfTestHWFailAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
RRH Alarm: RF Test Hardware Failure
"
::= { rrhTraps 53 }
 


lna1FailAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
RRH Alarm: LNA 1 Failure
"
::= { rrhTraps 54 }
 


lna2FailAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
RRH Alarm: LNA 2 Failure
"
::= { rrhTraps 55 }
 


extUnitCommsFailAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
RRH Alarm: External Unit Comms Failure
"
::= { rrhTraps 56 }
 


tx2TXFailAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
RRH Alarm: Transmitter 2 Failure
"
::= { rrhTraps 57 }
 


tx2GainFailAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
RRH Alarm: Tx 2 Gain Control Failed
"
::= { rrhTraps 58 }
 


tx2OpOverdriveAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
RRH Alarm: Tx 2 Digital Input Overdrive
"
::= { rrhTraps 59 }
 


unused5Alarm          NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
RRH Alarm: Unused 5
"
::= { rrhTraps 60 }
 


unused8Alarm          NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
RRH Alarm: Unused 8
"
::= { rrhTraps 61 }
 


unused50Alarm          NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
RRH Alarm: Unused 50
"
::= { rrhTraps 62 }
 


unused52Alarm          NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
RRH Alarm: Unused 52
"
::= { rrhTraps 63 }
 


lossOfSignal      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
CPRI Alarm.
"
::= { cpriTraps 1 }
 


lossOfFrame      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
CPRI Alarm.
"
::= { cpriTraps 2 }
 


remoteAlarmIndication      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
CPRI Alarm.
"
::= { cpriTraps 3 }
 


sapDefectIndication      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
CPRI Alarm.
"
::= { cpriTraps 4 }
 


rrhMsgQueueFull      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
RCM Alarm
"
::= { rcmTraps 1 }
 


rrhNotRespondingToCM      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
RCM Alarm
"
::= { rcmTraps 2 }
 


rrhTypeMismatch      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
RCM Alarm
"
::= { rcmTraps 3 }
 


rrhNotFound      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
RCM Alarm
"
::= { rcmTraps 4 }
 


rrhWrongConfiguration      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
RCM Alarm
"
::= { rcmTraps 5 }
 


rrhDetectionFailureAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
RCM Alarm
"
::= { rcmTraps 6 }
 


rcmHMFailureAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
RCM Alarm
"
::= { rcmTraps 7 }

ntpSyncFailureAlarm      NOTIFICATION-TYPE
OBJECTS                 {
                          trapIdentifier, trapEventTime,
                          trapNotificationType, trapManagedObjectInstance,
                          trapEventType, trapProbableCause,
                          trapSpecificProblem, trapPerceivedSeverity,
                          trapAdditionalText, trapAdditionalInformation
                        }

STATUS                  obsolete

DESCRIPTION
"
Alarm for indicating that the NTP sync is not happening for configured period of time.
"
::= { miscTraps 1 }


END
